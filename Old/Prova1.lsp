(defun c:Prova1 () 
  (command _picksyle 0)
  (setq Lista (ssget "x" (list '(0 . "insert") '(2 . "codpan")'(8 . "siglepan"))))
  (setq nr -1)
  (setq lstcodpan nil)
  (while (setq ent (ssname Lista (setq nr (+ 1 nr))))
    (setq lstcodpan (cons (List (cdr (assoc '1 (entget (entnext (entnext ent))))) (cdr (assoc '10 (entget ent)))) lstcodpan))      
  )
  
  (setq Lista (ssget "x" (list '(0 . "insert") '(2 . "codpan_r")'(8 . "siglepan"))))
  (setq nr -1)
  (setq lstcodpan_r nil)
  (while (setq ent (ssname Lista (setq nr (+ 1 nr))))
    (setq lstcodpan_r (cons (List (cdr (assoc '1 (entget (entnext (entnext ent))))) (cdr (assoc '10 (entget ent)))) lstcodpan_r))      
  )
  
  (setq Lista (ssget "x" (list '(0 . "insert") '(2 . "codpas")'(8 . "siglepan"))))
  (setq nr -1)
  (setq lstcodpas nil)
  (while (setq ent (ssname Lista (setq nr (+ 1 nr))))
    (setq lstcodpas (cons (List (cdr (assoc '1 (entget (entnext (entnext ent))))) (cdr (assoc '10 (entget ent)))) lstcodpas))      
  )
  
  (setq Lista (ssget "x" (list '(0 . "insert") '(2 . "codsvi")'(8 . "siglepan"))))
  (setq nr -1)
  (setq lstcodsvi nil)
  (while (setq ent (ssname Lista (setq nr (+ 1 nr))))
    (setq lstcodsvi (cons (List (cdr (assoc '1 (entget (entnext (entnext ent))))) (cdr (assoc '10 (entget ent)))) lstcodsvi))      
  )
  
  (setq Lista (ssget "x" (list '(0 . "insert") '(2 . "codsvi_r")'(8 . "siglepan"))))
  (setq nr -1)
  (setq lstcodsvi_r nil)
  (while (setq ent (ssname Lista (setq nr (+ 1 nr))))
    (setq lstcodsvi_r (cons (List (cdr (assoc '1 (entget (entnext (entnext ent))))) (cdr (assoc '10 (entget ent)))) lstcodsvi_r))      
  )
  (alert stop)
)
