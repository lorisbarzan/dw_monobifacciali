;Rev 2020
(DEFUN c:NEW1svi ()
  (start)
  (setq modalita (cadr (assoc 'percregtmp parametri)))
  (setq nome nil)
  (while (null nome)
(setq ent (car (entsel)))
    (if (= "codsvi" (cdr (assoc '2 (entget ent))))
      (setq nome (cdr (assoc '1 (entget (entnext ent)))))
    )
    (if (= "codsvi_R" (cdr (assoc '2 (entget ent))))
      (setq nome (cdr (assoc '1 (entget (entnext ent)))))
    )
    (if (= "rigatab" (cdr (assoc '2 (entget ent))))
      (setq nome (cdr (assoc '1 (entget (entnext (entnext ent))))))
    )
    (if (null nome)
      (alert "Selezione non valida")
    )
  )
  ;(SETQ NOME "PAN0002")
  (SETQ NEWP NIL)
  (IF (FINDFILE (STRCAT (cadr (assoc 'perc_sviluppi parametri)) NOME ".DWG"))
    (PROGN
      (INITGET "Si No")
      (setq sn (getkword "\nSviluppo già disegnato lo ridisegno [No/Si]:"))
      (if (= sn "Si")
	(progn
	  (vl-file-delete (STRCAT (cadr (assoc 'perc_sviluppi parametri)) NOME ".dwg"))
          (SETQ NEWP "T")
	)
	(progn
          (SETQ FILE (OPEN (cadr (assoc 'perc_sviluppi parametri)) "W"))  ;$$$$
	  (WRITE-LINE (STRCAT "_OPEN " (cadr (assoc 'perc_sviluppi parametri)) NOME) FILE)
	  (WRITE-LINE "_LAYOUT _SET A4" FILE)
	  (CLOSE FILE)
	)
      )
    )
    (PROGN
      (SETQ NEWP "T")
    )
  )
(IF NEWP
  (PROGN
    (SETQ FILE (OPEN (strcat "c:\\acad_tmp\\NEWPAN.SCR") "W"))
    (WRITE-LINE (strcat "_NEW "  "sviluppo") FILE)
    (WRITE-LINE "(LOAD\"ACAD\")" FILE)
        (WRITE-LINE "(setvar \"tilemode\" 1)" file)
(WRITE-LINE "(Setq Close_t t)" FILE)
    (WRITE-LINE (STRCAT "DISsvi " NOME ) FILE)
    
;;;    (WRITE-LINE (STRCAT "_LAYOUT _SET A4 _SAVEAS 2013 " (cadr (assoc 'perc_sviluppi parametri)) NOME " _close _y") FILE)
    (CLOSE FILE)
    (COMMAND "SCRIPT" "c:\\acad_tmp\\NEWPAN")
  )
  (COMMAND "SCRIPT" "c:\\acad_tmp\\OPENPAN")
)
  (stop)
)

(defun c:dissvi ()
  (start)
  (SETVAR "TILEMODE" 1)
  (setq modalita (cadr (assoc 'percregtmp parametri)))
  (setq nompan (getstring "\nCodice pannello <dwgname>"))
  (if (= "" nompan) (setq nompan (VL-FILENAME-BASE (getvar"dwgname"))))
  (dissvi nompan "n")
;;;  (SETQ *error* nil)

  (stop)
    ;(command"_close" "_y")
)

(defun dissvi (nompan mod)
;;;  (getstring)
  (SETVAR "TILEMODE" 1)
  (SETQ LUNG2 NIL)
  (SETQ PBASSO NIL)
  (setq lpele nil)
  (SETQ nonscanang NIL)
  (setq parametri (carica "parametri" ""))
  (if (/= "D" mod) (command"_erase" "_all" ""))
  (if (/= "D" mod) (if (null lispan_svx) (progn (setq tmp (carica_f "sviluppi" modalita)) (setq lispan_sv (carica_f+ "sviluppi_r" modalita))))
			 (setq lispan_sv (read (strcat "(" (leggi entsvi "sviluppi") ")")))
			 )
  (setq fronteoretro (carica_f "sviluppi_r" modalita))
  (setq fronteoretro (substr (car (nth 1 fronteoretro)) 1 2))
  (if (null prese) (setq prese (carica "prese" "")))
  (command"_point" "0,0,0")
  (setq basesel (entlast))
  (setq pan (assoc nompan lispan_sv))
  (if (null pan) (progn (alert "Pannello inesistente !!!") (exit)))
  (setq fpan "STD")
  (setq scver (cadr (assoc 'scalavertpanl parametri)))
  (if (/= "D" mod) 
		     (setq pp (list 0 150 0))(progn (setq pp (getpoint"\nPunto :")) (setq pp (list (car pp) (- (cadr pp) 0)))));70731
  (setq yd (+ (cadr pp) 350))
  (setq ppp pp)
  (if (null svilpan) (setq svilpan (carica "svilpan" "")))
  (IF (/= (nth 9 pan) "MAN")
    (foreach m svilpan
       (if (and (= (nth 9 pan) (car m)) )
;;;       (setq spsx (nth 2 m) spdx (nth 3 m))
       (if (= (substr (car pan) 1 2) fronteoretro)
	 (setq spsx (nth 8 m) spdx (nth 7 m) BORINF (NTH 9 M))
	 (setq spsx (nth 4 m) spdx (nth 3 m) BORINF (NTH 5 M))
	 )
     )
    )
    (progn
    (setq rigeman (read (nth 5 pan)))
    (setq spsx (nth 0 rigeman) spdx (nth 2 rigeman) BORINF (nth 2 rigeman))
    )
    )
    
;;;(setq *error* nil)
  (setq scver 1.0)
;;;  (setq N_ang (car (read (strcat "(" (nth 7 pan) ")"))))
    (setq n_lpan (nth 2 pan))
;;;  (if (> n_ang 225) ;2spess
;;;    (setq n_lpan (- (nth 2 pan) 1.4))
;;;    (setq n_lpan (nth 2 pan))
;;;    )
  (command"_line" "_non" (setq pt (list (CAR PP) yd 0))
	    "_non" (setq pt1 (polar pt 0 n_lpan))
	    "_non" (setq pt2 (polar pt1 (/ pi 2) (* scver (nth 4 pan))))
	    "_non" (setq pt3 (polar pt2 pi n_lpan))
	    "_c"
  )
;;;  (command"_line" "_non" (list (+ (car pt) spsx) (cadr pt)) "_non" (list (+ (car pt3) spsx) (cadr pt3)) "")
;;;  (command"_line" "_non" (list (- (car pt1) spdx) (cadr pt1)) "_non" (list (- (car pt2) spdx) (cadr pt2)) "")
  (setq pqfV PT3)
  (setq pqrv PT)
  (setq pqfh1 PT3)
  (setq pqfh2 PT)
  (command"_dim1" "_res" "PANNELLI")
;;;  (command"_dimlinear" "_non" pt1 "_non" pt2 "_V" "_non" (polar pt1 0 70))
;;;  (command"_dimlinear" "_non" pt "_non" pt1 "_h" "_non" (polar pt (* 3 (/ pi 2)) 70))
  
  (if (/= "D" mod) (if (null distpan_sv) (progn (setq tmp (carica_f "dibsvi" modalita)) (setq distpan_sv (carica_f+ "dibsvi_r" modalita))))
			  (progn
			    (setq distpan_s (read (strcat "(" (leggi entsvi "dibsvi") ")")))
			    (setq distpan_sv nil)
			    (foreach n distpan_s
			      (setq nn (cdr (cddddr n)))
			      (setq nn (cons (nth 1 n) nn))
			      (setq nn (cons (nth 0 n) nn))
			      (setq distpan_sv (cons nn distpan_sv))
			      )
			    ))
  (setq lposb nil)
  (if (/= "MAN" (nth 9 pan) )
    (progn
;;;      (setq svilpan (carica "svilpan" ""))
      (foreach n svilpan
	(if (and (= (nth 0 n) (nth 9 pan)) )
	  (if (= (substr (car pan) 1 2) fronteoretro)
	    (setq ltot (- (nth 2 pan) (setq dx (nth 8 n)) (setq sx (nth 7 n)));(- (nth 2 pan) (setq dx (nth 2 n)) (setq sx (nth 3 n)))
		hpan (- (nth 4 pan) (setq bx (nth 9 n)) (setq ax (nth 10 n))))
	    (setq ltot (- (nth 2 pan) (setq dx (nth 4 n)) (setq sx (nth 3 n)));(- (nth 2 pan) (setq dx (nth 2 n)) (setq sx (nth 3 n)))
		hpan (- (nth 4 pan) (setq bx (nth 5 n)) (setq ax (nth 6 n))))
	    )
	    
	  )
	)
      )
    (progn
          (setq rigeman (read (nth 5 pan)))
    ;(setq spsx (nth 0 rigeman) spdx (nth 2 rigeman) BORINF (nth 2 rigeman))

    (setq ltot (- (nth 2 pan) (setq dx (nth 0 rigeman)) (setq sx (nth 1 rigeman)));(- (nth 2 pan) (setq dx (nth 2 n)) (setq sx (nth 3 n)))
		hpan (- (nth 4 pan) (nth 2 rigeman) (setq ax (nth 3 rigeman))))
    )
    )
  (setq lposb (list 0 ltot))
  (setq lpqforio nil)
  (setq lpqforiv nil)
  (setq lpqforid nil)
  (foreach n distpan_sv
    (if  (and (= nompan (car n)) (or (= "000000001" (cadr n))(= "000000002" (cadr n))(= "000000003" (cadr n))))
	(progn
	      (setq pf1 (list (- (+ (CAR PT) 0 (nth 5 n)) 0)  (- (* scver (nth 6 n)) (- 0 yd) (- 0 (/ (nth 2 n) 2.0)) -7) 0)
		    pfq pt)
	      (command"_insert" (strcat "*innesto" (rtos (nth 2 n) 2 0)) "_non" pf1 1 0)
	  (setq lposb (cons (nth 5 n) lposb))
	      (setq pf2 pf1 pf3 pf1 pf4 pf1)
          (command"_dim1" "_res" "PRESE")
	  (setvar "dimlfac" (/ 1 scver))
;;;	  (command"_dimlinear" "_non" pt3 "_non" pf3 "_V" "_NON" (SETQ PQFV (POLAR PQFV pi 70)))
;;;	  (if (/= pf2 pf3) (command"_dimlinear" "_non" pF2 "_non" pf3 "_V" "_NON" PQFV))
	  (setvar "dimlfac" 1)
;;;   	      (command"_dimlinear" "_non" pfq "_non" pf1 "_h" "_NON" (SETQ PQFh1 (POLAR PQFh1 (* 1 (/ pi 2)) 70)))
;;;	      (if (/= pf1 pf2) (command"_dimlinear" "_non" pF1 "_non" pf2 "_h" "_NON" PQFh1))
	)
      )
      (if  (and (= nompan (car n)) (= "000000000" (cadr n)))
	(progn
	  (if (< 0 (nth 5 n))
	    
	    (if (= 0 (nth 6 n))
	      (progn
		(setq pf1 (list (- (+ (CAR PT) 0 (nth 8 n)) 0)  (- (* scver (+ BORINF (nth 9 n))) (- 0 yd) 0) 0)
		      pfq pt)
		(command"_circle" "_non" pf1 "_d" (nth 5 n))
		(setq lpele (cons pf1 lpele))
		(setq lpqforid (cons (list (list (entlast) pf1) (polar pf1 (* 7 (/ pi 4)) (nth 2 n))) lpqforid))
		;;;	      (command"_dimdiameter" (list (entlast) pf1) "_non" (polar pf1 (* 7 (/ pi 4)) (nth 2 n)))
		(setq pf2 pf1 pf3 pf1 pf4 pf1)
		)
	      (progn
		(setq pf1 (list (- (+ (CAR PT) 0 (nth 8 n)) (/ (nth 5 n) 2.0))  (- (* scver (+ BORINF (nth 9 n))) (- 0 yd) (/ (* scver (nth 6 n)) 2.0)) 0);massimofori
		      pfq pt)
		(setq lpele (cons (list (+ (car pf1) (/ (nth 5 n) 2.0)) (+ (/ (* scver (nth 6 n)) 2.0 )(* scver (cadr pf1)))) lpele))
		(command"_pline" "_non" pf1
			"_non" (setq pf2 (polar pf1 0 (nth 5 n)))
			"_non" (setq pf3 (polar pf2 (/ pi 2) (* scver (nth 6 n))))
			"_non" (setq pf4 (polar pf3 pi (nth 5 n)))
			"_c"
			)
		(setq lpqforiv (cons (list pf1 pf4 (POLAR pf1 pi 20))  lpqforiv))
		(setq lpqforio (cons (list pf3 pf4 (POLAR pf3 (* 1 (/ pi 2)) 20))  lpqforio))
		)
	      )
	    (progn
	      (setq pf1 (list (- (+ (CAR PT) 0 (nth 8 n)) 0)  (- (* scver (+ BORINF (nth 9 n))) (- 0 yd) 0) 0)
		      pfq pt)
	      (command"_insert" (rtos (nth 5 n) 2 0) "_non" pf1 "1" "1" "0")
	      		(setq lpele (cons pf1 lpele))

	      )
	    )
          (command"_dim1" "_res" "PRESE")
	  (setvar "dimlfac" (/ 1 scver))
	  ;(setq lpqforiv (cons (list pf1 pf4 (POLAR pf1 pi 20))  lpqforiv))
;;;	  (command"_dimlinear" "_non" pt3 "_non" pf3 "_V" "_NON" (SETQ PQFV (POLAR PQFV pi 70)))
;;;	  (if (/= pf2 pf3) (command"_dimlinear" "_non" pF2 "_non" pf3 "_V" "_NON" PQFV))
	  (setvar "dimlfac" 1)
	  ;(setq lpqforio (cons (list pf3 pf4 (POLAR pf3 (* 1 (/ pi 2)) 20))  lpqforio))
;;;   	      (command"_dimlinear" "_non" pfq "_non" pf1 "_h" "_NON" (SETQ PQFh1 (POLAR PQFh1 (* 1 (/ pi 2)) 70)))
;;;	      (if (/= pf1 pf2) (command"_dimlinear" "_non" pF1 "_non" pf2 "_h" "_NON" PQFh1))
	)
      )
    )
    (setq scantonature (carica "scantonature" ""))
  (if (findfile (strcat modalita "sviluppi_R.txt"))
    (progn
      (setq sviluppi_R (carica "sviluppi_R" modalita))
      (setq n_base (substr (car (last sviluppi_R)) 1 3))
      (if (= (substr (car pan) 1 3) n_base)   (setq scantonature nil)
	)
      )
    )


    (setq tipop (nth 9 (assoc nompan lispan_sv)))
  (if (/= tipop "MAN") (setq Tipop (Strcat "S" (substr tipop 2))))
  (setq lpsca nil)

  (if (/= "D" mod) (command"_zoom" "_e") (command"_zoom" "_w" (list (- (car pp) 300) (cadr pp)) (list (+ (car pp) 900) (+ (cadr pp) 2800)))
    )
    (setq lung1s nil)
  (setq angX 0)(setq ang_ 0)
    
      
    (if (and (/= "-" (nth 7 pan)) (/= 0 (car (read (strcat "(" (nth 7 pan) ")")))))
      (progn
	(SETQ ANG_ (setq ang (car (read (strcat "(" (nth 7 pan) ")")))))
	(setq lung2 (cadr (read (strcat "(" (nth 7 pan) ")"))))
	(setq lung1 (- (nth 2 pan) lung2 dx sx))
	(setq lung1s (- (nth 2 pan) lung2 dx))
	(if (< ang 180) (setq ang 0))
      )
      )
  (if lung1s (setq lung2s (- (nth 2 pan) lung1s)))
;43.7(if lung1s (setq lung2s (- (nth 2 pan) lung1s)))
    (setq nonscanang nil)
  (command"_zoom" "_e")
    (if (setq xdata (assoc (read (strcat tipop "_AS")) scantonature))
      (progn
	;NTD_as	74.2	180	5.1	270	30.5	0	60.9	270	23.7	0	18	270	20.1	0
        (if (and NIL (/= ang_ 0) (< lung1S 117));117
	  (progn
;;;	    (command"_line" "_non" (setq pp1 (polar pt3 (* (/ pi 2) 3) 12.3))
;;;		         "_non" (setq pp (polar pp1 0 (+ lung1S 15) ))
;;;		         "_non" (polar pp (/ pi 2) 12.3)
;;;		    ""
;;;	    
;;;	    )
;;;	    (setq nonscanang t)
	    (SETQ DADJOASID "")
	    )
	  (progn
	(if (and (/= ang_ 0) (< lung1S 29))
	  (PROGN
	      (command"_line" "_non" (setq pp1 (polar pt3 (* (/ (nth 2 xdata) 180.0) pi) (nth 1 xdata) ))
		         "_non" (setq psca (setq pp (polar pp1 (* (/ (nth 4 xdata) 180.0) pi)(+ lung1S 15) ))))
	      (if (nth 5 xdata) (command "_non" (setq pp (polar pp (* (/ (nth 6 xdata) 180.0) pi) (nth 5 xdata) ))))
	      (setq nonscanang t)
	    )
	  (PROGN
              (command"_line" "_non" (setq pp1 (polar pt3 (* (/ (nth 2 xdata) 180.0) pi) (nth 1 xdata) ))
		         "_non" (setq psca (setq pp (polar pp1 (* (/ (nth 4 xdata) 180.0) pi)(nth 3 xdata) ))))
	      (if (nth 5 xdata) (command "_non" (setq pp (polar pp (* (/ (nth 6 xdata) 180.0) pi) (nth 5 xdata) ))))
	    )
	  )
	  
	(if (nth 7 xdata) (command "_non" (setq pp (polar pp (* (/ (nth 8 xdata) 180.0) pi) (nth 7 xdata) ))))
	(if (nth 9 xdata) (command "_non" (setq pp (polar pp (* (/ (nth 10 xdata) 180.0) pi) (nth 9 xdata) ))))
	(if (nth 11 xdata) (command "_non" (setq pp (polar pp (* (/ (nth 12 xdata) 180.0) pi) (nth 11 xdata) ))))
	(if (nth 13 xdata) (command "_non" (setq pp (polar pp (* (/ (nth 14 xdata) 180.0) pi) (nth 13 xdata) ))))
	(command "")
	(setq lpsca (cons psca lpsca))
	  (setq dist_as (- (car pt3) (car pp)))))
	(command"_zoom" "_c" pt3 600)
	(command"_trim" "" "_non" pt3 pt3 "")
	(COMMAND"_ZOOM" "_P")
	)
      )
    (if (setq xdata (assoc (read (strcat tipop "_AD")) scantonature))
      (progn
        (if (and NIL (/= ang_ 0) (< lung2S 86));86
	  (progn
;;;	    (ALERT "OK")
;;;	    (command"_line" "_non" (setq pp1 (polar pt2 (* (/ pi 2) 3) 12.3))
;;;		         "_non" (setq pp (polar pp1 pi (+ lung2 DX 15) ))
;;;		         "_non" (polar pp (/ pi 2) 12.3)
;;;		    ""
;;;	    
;;;	    )
	    (setq nonscanang t)
	    )
	  (progn
;;;(ALERT "OK1")
	    (if (and (/= ang_ 0) (< lung2S 86));86
	      (PROGN
		(setq nonscanang t)
		(command"_line" "_non" (setq ppp_d (setq pp (polar pt2 (/ (* pi (nth 2 xdata)) 180) (+ lung2 DX 15) )))
			"_non" (setq psca (setq pp (polar pp (/ (* pi (nth 4 xdata)) 180)(nth 3 xdata) ))))
		(if (nth 5 xdata) (command "_non" (setq pp (polar pp (/ (* pi (nth 6 xdata)) 180) (+ lung2 DX 15 (nth 5 xdata)(- 0 (nth 1 xdata)))   ))))
		)
	      (PROGN
		(command"_line" "_non" (setq ppp_d (setq pp (polar pt2 (/ (* pi (nth 2 xdata)) 180) (nth 1 xdata) )))
			"_non" (setq psca (setq pp (polar pp (/ (* pi (nth 4 xdata)) 180)(nth 3 xdata) ))))
		(if (nth 5 xdata) (command "_non" (setq pp (polar pp (/ (* pi (nth 6 xdata)) 180) (nth 5 xdata) ))))
		)
	      )
	(if (nth 7 xdata) (command "_non" (setq pp (polar pp (/ (* pi (nth 8 xdata)) 180) (nth 7 xdata) ))))
	(if (nth 9 xdata) (command "_non" (setq pp (polar pp (/ (* pi (nth 10 xdata)) 180) (nth 9 xdata) ))))
	(if (nth 11 xdata) (command "_non" (setq pp (polar pp (/ (* pi (nth 12 xdata)) 180) (nth 11 xdata) ))))
	(if (nth 13 xdata) (command "_non" (setq pp (polar pp (/ (* pi (nth 14 xdata)) 180) (nth 13 xdata) ))))
	(command "")
	(setq lpsca (cons psca lpsca))
	(setq dist_ad (- (car pt2) (car ppp_d)))
	)
	  
	  )
	  (command"_zoom" "_c" pp 600)
	(command"_trim" "" "_non" pt2 pt2 "")(COMMAND"_ZOOM" "_P")
	)
      )
     
     (if (setq xdata (assoc (read (strcat tipop "_BD")) scantonature))
      (progn
        (if (and NIL  (/= ang_ 0) (< lung2S 86));86
	  (progn
;;;	    (command"_line" "_non" (setq pp1 (polar pt1 (* (/ pi 2) 1) 12.3))
;;;		         "_non" (SETQ PSCA (setq pp (polar pp1 pi (+ lung2 DX 15) )))
;;;		         "_non" (polar pp (* (/ pi 2) 3) 12.3)
;;;		    ""
;;;	    
;;;	    )
;;;	    (setq lpsca (cons psca lpsca))
	    (setq nonscanang t)
	    )
	  (progn
	    (if (and (/= ang_ 0) (< lung2S 86));86
	      (PROGN
		(setq nonscanang t)
		(command"_line" "_non" (setq ppp_d (setq pp (polar pt1  (/ (* pi (nth 2 xdata)) 180) (+ lung2 DX 15)) ))
			"_non" (setq psca (setq pp (polar pp  (/ (* pi (nth 4 xdata)) 180)(nth 3 xdata) ))))
		(if (nth 5 xdata) (command "_non" (setq pp (polar pp  (/ (* pi (nth 6 xdata)) 180)(+ lung2 DX 15 (- 0 (nth 1 xdata))(nth 5 xdata) ) ))))
		)
	      (PROGN
		(command"_line" "_non" (setq ppp_d (setq pp (polar pt1  (/ (* pi (nth 2 xdata)) 180) (nth 1 xdata)) ))
			"_non" (setq psca (setq pp (polar pp  (/ (* pi (nth 4 xdata)) 180)(nth 3 xdata) ))))
		(if (nth 5 xdata) (command "_non" (setq pp (polar pp  (/ (* pi (nth 6 xdata)) 180)(nth 5 xdata) ))))
		)
	      )
	(if (nth 7 xdata) (command "_non" (setq pp (polar pp  (/ (* pi (nth 8 xdata)) 180)  (nth 7 xdata) ))))
	(if (nth 9 xdata) (command "_non" (setq pp (polar pp  (/ (* pi (nth 10 xdata)) 180)  (nth 9 xdata) ))))
	(if (nth 11 xdata) (command "_non" (setq pp (polar pp  (/ (* pi (nth 12 xdata)) 180)  (nth 11 xdata) ))))
	(if (nth 13 xdata) (command "_non" (setq pp (polar pp (/ (* pi (nth 14 xdata)) 180)  (nth 13 xdata) ))))
	(command "")
	(setq lpsca (cons psca lpsca))
	(setq dist_bd (- (car pt1) (car ppp_d))))
	  )
	(command"_zoom" "_c" pp 600)(command"_trim" "" "_non" pt1 pt1 "")(COMMAND"_ZOOM" "_P")
	)
      )
  
  (if (setq xdata (assoc (read (strcat tipop "_BS")) scantonature))
      (progn
        (if (and NIL (/= ang_ 0) (< lung1S 29));117
	  (progn
;;;	    (command"_line" "_non" (setq pp1 (polar pt (* (/ pi 2) 1) 12.3))
;;;		         "_non" (SETQ PSCA (setq pp (polar pp1 0 (+ lung1S 15) )))
;;;		         "_non" (polar pp (* (/ pi 2) 3) 12.3)
;;;		    ""
;;;	    
;;;	    )
;;;	    (setq lpsca (cons psca lpsca))
	    (setq nonscanang t)
	    )
	  (progn
	    (if (and (/= ang_ 0) (< lung1S 29))
	      (PROGN
	    (setq nonscanang t)
	(command"_line" "_non" (setq ppp_d (setq pp (polar pt (- (/ (* pi (nth 2 xdata)) 180) 0) (+ lung1S 15))))
		         "_non" (setq psca (setq pp (polar pp (- (/ (* pi (nth 4 xdata)) 180) 0)(nth 3 xdata) ))))
	(if (nth 5 xdata) (command "_non" (setq pp (polar pp (- (/ (* pi (nth 6 xdata)) 180) 0) (+ (NTH 1 XDATA) (- 0 (NTH 5 XDATA)) lung1S 15) ))))
	)
	      (PROGN
	      	(command"_line" "_non" (setq ppp_d (setq pp (polar pt (- (/ (* pi (nth 2 xdata)) 180) 0) (nth 1 xdata))))
		         "_non" (setq psca (setq pp (polar pp (- (/ (* pi (nth 4 xdata)) 180) 0)(nth 3 xdata) ))))
	(if (nth 5 xdata) (command "_non" (setq pp (polar pp (- (/ (* pi (nth 6 xdata)) 180) 0) (nth 5 xdata) ))))
)
	      )
	(if (nth 7 xdata) (command "_non" (setq pp (polar pp (- (/ (* pi (nth 8 xdata)) 180) 0) (nth 7 xdata) ))))
	(if (nth 9 xdata) (command "_non" (setq pp (polar pp (- (/ (* pi (nth 10 xdata)) 180) 0) (nth 9 xdata) ))))
	(if (nth 11 xdata) (command "_non" (setq pp (polar pp (- (/ (* pi (nth 12 xdata)) 180) 0) (nth 11 xdata) ))))
	(if (nth 13 xdata) (command "_non" (setq pp (polar pp (- (/ (* pi (nth 14 xdata)) 180) 0) (nth 13 xdata) ))))
	(command "")
	(setq lpsca (cons psca lpsca))
	(setq dist_bs (- (car pt) (car ppp_d)))))
	(command"_zoom" "_c" pp 600)(command"_trim" "" "_non" pt "_non"pt "")(COMMAND"_ZOOM" "_P")
;;;	(command"_trim" "" "_non" pfq "")
	)
      )
    (IF (NULL LUNG2) (SETQ LUNG2 0))
    (setq lung1s nil)
    (if (and (/= "-" (nth 7 pan)) (/= 0 (car (read (strcat "(" (nth 7 pan) ")")))))
      (progn
	(setq ang (car (read (strcat "(" (nth 7 pan) ")"))))
	(setq lung2 (cadr (read (strcat "(" (nth 7 pan) ")"))))
	(setq lung1s (- (nth 2 pan) lung2))
	(if (< ang 180) (setq ang 0))
      )
      )
      (if (= (substr nompan 1 2) fronteoretro) (setq nonscanang t lung1s (- (nth 2 pan) lung2)))

  (if lung1s (setq lung2s (- (nth 2 pan) lung1s)))
  (if (null dist_as) (setq dist_as 0))
  (if (null dist_ad) (setq dist_ad 0))
    (if (and lung1s ;(or (and (> ang 180) (> lung1s (- (abs dist_as) 15 ))) (and (< ang 180) (> lung1s (+ 0 (abs dist_as)))))
             ;(or (and (> ang 180) (> lung2s (+ 15 (abs dist_ad)))) (and (< ang 180) (> lung2s (+ 0 (abs dist_ad)))))
	     )
      (progn
	(IF (/= ANG 0)
	  (PROGN
	  (if (null nonscanang)
	    (progn
	    (if (> ang 225);2spess
	      (setq palto (list (- (+ lung1s (car pt3)) 0.7) (cadr pt3)))
	      (setq palto (list (+ lung1s (car pt3)) (cadr pt3)))
	      )
	          	(command"_insert" (strcat "*scan_a_270") "_non" (list (+ lung1s (car pt3)) (cadr pt3)) "1" "0")
	(command"_zoom" "_c" (list (+ lung1s (car pt3)) (cadr pt3)) 50)
	(command"_trim" "" "_non" (list (+ lung1s (car pt3)) (cadr pt3)) "")(COMMAND"_ZOOM" "_P")
      	(command"_insert" (strcat "*scan_b_270" ) "_non" (setq pbasso (list (+ lung1s (car pt3)) (cadr pt1))) "1" "0")
	(command"_zoom" "_c" (list (+ lung1s (car pt3)) (cadr pt1)) 50)
	(command"_trim" "" "_non" (list (+ lung1s (car pt3)) (cadr pt1)) "")(COMMAND"_ZOOM" "_P")
;;;	(command "_circle" "_non" (list (+ (car pt3) lung1s +44.8) (- (cadr pt2) 33.6)) f1)

;;;	(setq ang1 (+ (/ (- 180 ang) 2) 90))
;;;	(setq ang2 (- (- 180 (/ (- 180 ang) 2)) 90))
;;;	(setq ang1 (* (/ ang1 180.0) pi))
;;;	(setq ang2 (* (/ ang2 180.0) pi))
;;;	(setq p (polar palto (* 3 (/ pi 2)) 12.7))
;;;	(setq p1 (inters palto pt3 p (polar p ang1 25) nil))
;;;	(setq p2 (inters palto pt3 p (polar p ang2 25) nil))
;;;	(command"_arc" "_c" "_non" (SETQ PKK1 (polar palto (* 3 (/ pi 2)) 12)) "_non" (SETQ PKK2 (polar (polar palto (* 3 (/ pi 2)) 12) ang2 1))
;;;		"_non"  (SETQ PKK3 (polar (polar palto (* 3 (/ pi 2)) 12) ang1 1)))
;;;	(setq cer (entlast))
;;;	(command"_line" "_non" p "_non" p1 "")
;;;	(setq l1 (entlast))
;;;	(command"_line" "_non" p "_non" p2 "")
;;;	(setq l2 (entlast))
;;;	(command"_zoom" "_c" palto 50)
;;;	(command"_trim" "" "_non" palto "")(COMMAND"_ZOOM" "_P")
;;;	(COMMAND"_ZOOM" "_C" P 50)
;;;	(command"_trim" cer "" "_NON" (LIST L1 p) "_NON" (LIST L2 p) "")(COMMAND"_ZOOM" "_P")
;;;	(command"_arc" "_c" "_non" (polar palto (* 3 (/ pi 2)) 12) "_non" (cdr (assoc '10 (entget l2)))
;;;		"_non"  (cdr (assoc '10 (entget l1))))
;;;	(COMMAND"_ZOOM" "_P")
;;;	(entdel cer)
;;;
;;;	(if (> ang 225);2spess
;;;	  (setq pbasso (list (- (+ lung1s (car pt3)) 0.7) (cadr pt1)))
;;;	  (setq pbasso (list (+ lung1s (car pt3)) (cadr pt1)))
;;;	  )
;;;	(setq p (polar pbasso (* 1 (/ pi 2)) 12))
;;;	(setq p1 (inters pbasso pt1 p (polar p (- ang1 pi ) 12.7) nil))
;;;	(setq p2 (inters pbasso pt1 p (polar p (- ang2 pi ) 12.7) nil))
;;;	(command"_circle" "_non" (polar pbasso (* 1 (/ pi 2)) 11.7) 1)
;;;	(setq cer (entlast))
;;;	(command"_line" "_non" p "_non" p1 "")
;;;	(setq l1 (entlast))
;;;	(command"_line" "_non" p "_non" p2 "")
;;;	(setq l2 (entlast))
;;;	(command"_zoom" "_c" pbasso 50)
;;;	(command"_trim" "" "_non" pbasso "")(COMMAND"_ZOOM" "_P")
;;;	(command"_zoom" "_c" p 50)
;;;	(command"_trim" cer "" (LIST L1 p) (LIST L2 p) "")(COMMAND"_ZOOM" "_P")
;;;	(command"_arc" "_c" "_non" (polar pbasso (* 1 (/ pi 2)) 11.7) "_non" (cdr (assoc '10 (entget l2)))
;;;		"_non"  (cdr (assoc '10 (entget l1))))
;;;	(entdel cer)
;;;;;;	(setq f1 (cadr (assoc 'ForoVitiAngolo parametri)))
;;;;;;	(command "_circle" "_non" (list (+ (car pt3) lung1s -57.7) (- (cadr pt2) 33.6)) f1)
;;;;;;	(command "_circle" "_non" (list (+ (car pt3) lung1s +44.8) (- (cadr pt2) 33.6)) f1)
	)
	    ))
	(progn
;;;	  	(setq f1 (cadr (assoc 'ForoVitiAngolo parametri)))
(if (null nonscanang)
  (PROGN
      	(command"_insert" (strcat "*scan_a_" (rtos ang 2 0)) "_non" (list (+ lung1s (car pt3)) (cadr pt3)) "1" "0")
	(command"_zoom" "_c" (list (+ lung1s (car pt3)) (cadr pt3)) 50)
	(command"_trim" "" "_non" (list (+ lung1s (car pt3)) (cadr pt3)) "")(COMMAND"_ZOOM" "_P")
	(command "_circle" "_non" (list (+ (car pt3) lung1s -57.7) (- (cadr pt2) 33.6)) f1)
      	(command"_insert" (strcat "*scan_b_" (rtos ang 2 0)) "_non" (setq pbasso (list (+ lung1s (car pt3)) (cadr pt1))) "1" "0")
	(command"_zoom" "_c" (list (+ lung1s (car pt3)) (cadr pt1)) 50)
	(command"_trim" "" "_non" (list (+ lung1s (car pt3)) (cadr pt1)) "")(COMMAND"_ZOOM" "_P")
	(command "_circle" "_non" (list (+ (car pt3) lung1s +44.8) (- (cadr pt2) 33.6)) f1)
    )
  )
	)
	  )
	)
      )
;;;  (setq *error* nil)
     
     
;;;    (command "_circle" "_non" (list (- (car pt2) 10) (+ (cadr pt) 10)) "3")
    ;fori viti
    
    (setvar"cmdecho" 1)
  (setq grexp (selez basesel))
  (command"_select" grexp "")
  (setq grline (ssget "_p" (list '(0 . "LINE"))))
  (setq grarc (ssget "_p" (list '(0 . "ARC"))))
  (while (and grline (setq line (ssname grline 0)))
       (command"_pedit" line "_y" "_j" grexp "" "" "")
   (setq grexp (selez basesel))
  (command"_select" grexp "")
  (setq grline (ssget "_p" (list '(0 . "LINE"))))
  (setq grarc (ssget "_p" (list '(0 . "ARC"))))

   )
  (command"_select" grexp "")
  (if (setq grline (ssget "_p" (list '(0 . "LINE")))) (alert "Nello sviluppo esistono LINEE !!!"))
  (if (setq grarc (ssget "_p" (list '(0 . "ARC")))) (alert "Nello sviluppo esistono ARCHI !!!"))
(if (setq grpap (ssget "_p" (list '(0 . "LWPOLYLINE") '(70 . 128))))
  (progn
;;;    (alert "Nello sviluppo esistono POLYLINEE APERTE !!!")
    (cond ((= (sslength grpap) 1)
;;;	   (alert "1")
	   (setq pol (ssname grpap 0))
;;;	   (command"_line" "_non" "0,0,0" "_non" (cdr (assoc '10 (entget pol))) "")
;;;	   (command"_line" "_non" "0,0,0" "_non" (cdr (assoc '10 (reverse (entget pol)))) "")
	   (command"_trim" pol "" (list pol (cdr (assoc '10 (entget pol)))) (list pol (cdr (assoc '10 (reverse (entget pol))))) "")
	  )
	  ((= (sslength grpap) 2)
;;;	   (alert "2")
	   (setq pol1 (ssname grpap 0))
	   (setq pol2 (ssname grpap 1))
	   (command"_trim" pol1 "" (list pol2 (cdr (assoc '10 (entget pol2)))) (list pol2 (cdr (assoc '10 (reverse (entget pol2))))) "")
	   (command"_trim" pol2 "" (list pol1 (cdr (assoc '10 (entget pol1)))) (list pol1 (cdr (assoc '10 (reverse (entget pol1))))) "")
	   (command"_pedit" pol1 "_J" pol2 "" "")
           (if (setq grpap (ssget "_p" (list '(0 . "LWPOLYLINE") '(70 . 128)))) (alert "Nello sviluppo esistono POLYLINEE APERTE !!!"))
	   
	  )
	  (t (alert "t"))
      )
    
    
    )
  )
  (setq grpch NIL)
  (SETQ grpca NIL)
  (setq grexp (selez basesel))
  (command"_select" grexp "")
  (setq lpol nil)
  (setq grpch (ssget "_p" (list '(0 . "LWPOLYLINE") '(70 . 129))))
  (if (null grpch) (setq grpch (ssget "_p" (list '(0 . "LWPOLYLINE") '(70 . 1)))))
  ;chiusura due polilinee
  (if (null grpch)
    (progn
      (setq grpca (ssget "_p" (list '(0 . "LWPOLYLINE") '(70 . 128))))
      (if (null grpca) (setq grpca (ssget "_p" (list '(0 . "LWPOLYLINE") '(70 . 0)))))
      (if (and grpca (= 2 (sslength grpca)))
	(progn
(alert "2 Polilinee incrociate")
;;;          (setq pol0 (ssname grpca 0))
;;;          (setq lpol0 nil)
;;;          (foreach p (entget pol0) (if (= '10 (car p)) (setq lpol0 (cons (cdr p) lpol0))))
;;;          (setq pol1 (ssname grpca 1))
;;;          (setq lpol1 nil)
;;;          (foreach p (entget pol1) (if (= '10 (car p)) (setq lpol1 (cons (cdr p) lpol1))))
;;;          (command"_trim" pol0 "" (list pol1 (car lpol1)) (list pol1 (last lpol1)) "")
;;;          (command"_trim" pol1 "" (list pol0 (car lpol0)) (list pol0 (last lpol0)) "")
;;;(command"_pedit" pol1 "_J" pol0 "" "")

	  )
	)
      )
    )
    (setq grexp (selez basesel))
  (command"_select" grexp "")
  (setq lpol nil)

    (setq grpch (ssget "_p" (list '(0 . "LWPOLYLINE") '(70 . 129))))
  (if (null grpch) (setq grpch (ssget "_p" (list '(0 . "LWPOLYLINE") '(70 . 1)))))

  (cond ((or (null grpch) (= 0 (sslength grpch))) (alert "nessuna polilinea"))
	((= 1 (sslength grpch)) (setq lpol (cons (list 10 (setq polext (ssname grpch 0))) lpol)))
	(t (setq lpol nil) (setq lpt nil) (setq nrp -1)
	 (repeat (sslength grpch)
	   (setq lpt nil)
	   (setq pol (ssname grpch (setq nrp (+ 1 nrp))))
	   (setq lpol (cons (list (length (entget pol)) pol) lpol))
	   )
	 )
	)
    (setq lpol (vl-sort lpol (function (lambda (e1 e2) (> (car e1) (car e2))))))
;;;  ))
  (setq pol (cadr (car lpol)))
  (setq lpt nil)
  (setq grexp (selez basesel))
  (entdel basesel)
  (command"_select" pol "_wp")
  (setq oldv (list 0 0 0))
  (foreach v (entget pol)
    (if (and (= '10 (car v))(/= (distance (cdr v) oldv) 0) )
      (command"_non" (setq oldv (cdr v)))
      )
    )
  (command"" "")
;;;  (command"_select" "_p" "_r" pol "")
  
  (setq grres (ssget "_p"))
  (if (/= (sslength grres) (sslength grexp))
    (progn
      ;(alert"Eliminati oggetti fuori dal contorno")
      (command"_erase" grexp "_r" grres "")
      )
    )
;;;  (if (and grres (> (sslength grres) 0))
;;;    (progn
;;;      (alert"Eliminati oggetti fuori dal contorno")
;;;      (command"_erase" grres "")
;;;      )
;;;    )

  (command"_undo" "_g")
    ;qui
  ;fronteoretro
  (if (= fronteoretro (substr (car pan) 1 2))
    (progn
      (command"_mirror" (ssget "x") "" "_non" (list (/ (+ (car pt) (car pt1)) 2) (cadr pt)) "_non" (list (/ (+ (car pt) (car pt1)) 2) (cadr pt2)) "_Yes")
      )
    )

    (setq gr (ssget "_X" (list '(0 . "DIMENSION"))))
    (if gr (command"_erase" gr ""))
  (SETVAR"TILEMODE"0)
  (COMMAND"_ERASE" "_ALL" "")
    (SETVAR"TILEMODE"1)
(setvar "cmdecho" 1)
;;;    (command"_move" "_all" "" "_non" pt3 "_non" "0,0,0")
;;;    (command"_rotate" "_all" "" "_non" "0,0,0" 90)
;;;  (if (and (/= mod "D") t)
;;;    (if (findfile (strcat (cadr (assoc 'perc_svi_dxf parametri)) nompan ".dxf"))
;;;        (command"_saveas" "dxf" "_v" "R12" 16 (strcat (cadr (assoc 'perc_svi_dxf parametri)) nompan) "_y")
;;;        (command"_saveas" "dxf" "_v" "R12" 16 (strcat (cadr (assoc 'perc_svi_dxf parametri)) nompan))
;;;    )
;;;  )
  (if (and (/= mod "D") t)
    (progn
    (if (findfile (strcat (cadr (assoc 'perc_svi_dxf parametri)) nompan ".dxf"))
      (vl-file-delete (strcat (cadr (assoc 'perc_svi_dxf parametri)) nompan ".dxf"))
      )
    ;inizio rotazione e triangolo

 (setq gr (ssget "x" (list '(0 . "lwpolyline"))))
  (setq nr -1)
  (list listpt nil)
  (while (setq ent (ssname gr (setq nr (+ 1 nr))))
    (foreach e (entget ent)
      (if (= 10 (car e)) (setq listpt (cons (cdr e) listpt)))
    )
  )
  (setq lisx (vl-sort listpt (function (lambda (e1 e2) (> (CAR e1) (CAR e2))))))
  (setq xmin (car (last lisx)))
  (setq xmax (car (cAR lisx)))
  (setq lisy (vl-sort listpt (function (lambda (e1 e2) (> (CAdR e1) (CAdR e2))))))
  (setq ymin (car (last lisy)))
  (setq ymax (car (cAR lisy)))
  (setq pt (list (/ (+ xmin xmax) 2) (+ 400 ymin)))
  (setq lpos '((0 . 0) (-20 . 0) (20 . 0) (0 . 20)(0 . -20) (20 . 20)(-20 . -20)
	       (-40 . 0) (40 . 0) (0 . 40)(0 . -40) (40 . 40)(-40 . -40)
	       (-60 . 0) (60 . 0) (0 . 60)(0 . -60) (60 . 60)(-60 . -60)
	       (-80 . 0) (80 . 0) (0 . 80)(0 . -80) (80 . 80)(-80 . -80)
	       (-100 . 0) (100 . 0) (0 . 100)(0 . -100) (100 . 100)(-100 . -100)
	       (-120 . 0) (120 . 0) (0 . 120)(0 . -120) (120 . 120)(-120 . -120)
	       (-150 . 0) (150 . 0) (0 . 150)(0 . -150) (150 . 150)(-150 . -150)
	       (-200 . 0) (200 . 0) (0 . 200)(0 . -200) (200 . 200)(-200 . -200)
	       (400 . 400)))
  (setq gre t)
  (setq pos 0)
  (while gre
    (setq s (nth pos lpos))
    (setq ptx (list (+ (car pt) (car s)) (+ 400 (cadr pt) (cdr s))))
    (setq gre (ssget "_c" (list (- (car ptx) 53) (cadr ptx))
		     (setq pctr (list (+ (car ptx) 53) (+ 75 (cadr ptx))))))
(if (> (car pctr) xmax)  (progn
			       (setq file (open "c:/acad_tmp/registo.txt" "a"))
			   (write-line (getvar"dwgname") file)
			   (close file)
			       (setq gre nil)
			       )
      )
    ;(command"_line" (list (- (car ptx) 53) (cadr ptx)) (list (+ (car ptx) 53) (+ 75 (cadr ptx)))  "")
;;;    (if (null gre)
;;;      (progn
;;;	(Command"_line" "0,0,0" ptx "")
;;;	(command"_line" (list (- (car ptx) 53) (cadr ptx)) (list (+ (car ptx) 53) (+ 75 (cadr ptx)))  "")
;;;	)
;;;      )
    (setq pos (+ 1 pos))
    (if (> (+ 1 pos) (length lpos))(progn
			       (setq file (open "c:/acad_tmp/registo.txt" "a"))
			   (write-line (getvar"dwgname") file)
			   (close file)
			       (setq gre nil)
			       )
      )
    
    )
  (command"_insert" "*tri.dwg" "_non" ptx "1" "0")
  (command"_rotate" "_all" "" "_non" (list xmin ymin) "90")



    ;fine rotazione e triangolo
    
;;;        (command"_wblock" (strcat (cadr (assoc 'perc_svi_dxf parametri)) nompan ".dxf") "" "" "0,0,0" "_all" "" "_y")
        (command"_wblock" (strcat (cadr (assoc 'perc_svi_dxf parametri)) nompan ".dxf") "" "" "0,0,0"  "_all" "")
    )
  )
    (command"_undo" "_e")
  (command"_u")
(command"_zoom" "_e")
(foreach l lpqforid
  (setq ll l)(if (/= (cdr (assoc '40 (entget (car (car ll))))) 9.5) (command"_dim1" "_diameter" (car ll) "" "_non" (polar (cadr (car ll)) (/ pi 6) 20)))
  )
  
(foreach l lpqforiv
  
  (command"_dimlinear" "_non" (nth 0 l) "_non" (nth 1 l) "_V" "_NON" (nth 2 l))
  )
(foreach l lpqforio
   (command"_dimlinear" "_non" (nth 0 l) "_non" (nth 1 l) "_h" "_NON" (nth 2 l))
)



  
;;;    (command"_saveas" "dxf" "_v" "R14" 16 (strcat (cadr (assoc 'perc_svi_dxf parametri)) nompan))
;;;    (IF (> (GETVAR"CMDACTIVE") 0) (COMMAND""))
;    (command"_rotate" "_all" "" "_non" PT3 90)
;;;    (exit)
;;;    (distbase "no" (nth 0 pan) (list 781.4890 -12.8831 0) 0.3)
(setq lispqxtot nil)
(setq lispqytot nil)
  (foreach n (entget pol)
    (if (= 10 (car n))
      (progn
	(if (null (member (atof (rtos (car (cdr n)) 2 1)) lispqxtot)) (setq lispqxtot (cons (atof (rtos (car (cdr n)) 2 1)) lispqxtot)))
	(if (null (member (atof (rtos (cadr (cdr n)) 2 1)) lispqytot)) (setq lispqytot (cons (atof (rtos (cadr (cdr n)) 2 1)) lispqytot)))
	) 
      )
    )
  (setq lispqxtot (vl-sort lispqxtot (function (lambda (e1 e2) (> e1 e2)))))
  (setq lispqytot (vl-sort lispqytot (function (lambda (e1 e2) (> e1 e2)))))
;;;(command"_dimlinear" "_non" (list  "_non" pt2 "_V" "_non" (polar pt1 0 70))  
  (setq pbs (list (last lispqxtot) (last lispqytot)))
  (setq pas (list (last lispqxtot) (car lispqytot)))
  (setq pbd (list (car lispqxtot) (last lispqytot)))
  (IF LUNG1S
    (PROGN
      (COMMAND"_LINE" "_NON" (LIST (+ (CAR PAS) LUNG1S) (CADR PAS))   "_NON" (LIST (+ (CAR PBS) LUNG1S) (CADR PBS)) "")
      (COMMAND"_CHPROP" (ENTLAST) "" "_LT" "HIDDEN" "")
      (IF (NULL PBASSO) (SETQ PBASSO (LIST (+ (CAR PBS) LUNG1S) (CADR PBS))))
      )
    )
  ;QUOTE TOTALI
  (command "_dimlinear" "_non" pbs "_non" pbd "_h" "_non" (list (car pbs) (- (cadr pbs) 300)))
  (if pbasso
    (command"_dimlinear" "_non" pbs "_non" pbasso "_h" "_non" (list (car pbs) (- (cadr pbs) 100))
    "_dimlinear" "_non" pbasso "_non" pbd "_h" "_non" (list (car pbs) (- (cadr pbs) 100)))
    
    )
  (command"_dimlinear" "_non" pbs "_non" pas "_v" "_non" (list (- (car pbs) 200) (- (cadr pbs) 0))
    )
  (setq lxpsca nil)
  (setq lypsca nil)
  (foreach n lpsca
    (if (null (member (atof (rtos (car n) 2 1)) lxpsca)) (setq lxpsca (cons (atof (rtos (car n) 2 1)) lxpsca) ))
    (if (null (member (atof (rtos (cadr n) 2 1)) lypsca)) (setq lypsca (cons (atof (rtos (cadr n) 2 1)) lypsca) ))
    )
  ;QUITE POSIZIONE SCATOLA
(setq lxpsca (vl-sort lxpsca (function (lambda (e1 e2) (> e1 e2)))))
(setq lypsca (vl-sort lypsca (function (lambda (e1 e2) (> e1 e2)))))
  (if lypsca
    (command"_dimlinear" "_non" pbs "_non" (list (car pbs) (last lypsca)) "_v" "_non" (list (- (car pbs) 100) (- (cadr pbs) 0))
	    "_dimlinear" "_non" (list (car pbs) (last lypsca)) "_non" (list (car pbs) (car lypsca)) "_v" "_non" (list (- (car pbs) 100) (- (cadr pbs) 0))
	    "_dimlinear" "_non" (list (car pbs) (car lypsca)) "_non" pas "_v" "_non" (list (- (car pbs) 100) (- (cadr pbs) 0))
	    )
    )
  (if lxpsca
    (command"_dimlinear" "_non" pbs "_non" (list (last lxpsca) (cadr pbs)) "_h" "_non" (list (- (car pbs) 0) (- (cadr pbs) 200))
	    "_dimlinear" "_non" (list (last lxpsca) (cadr pbs)) "_non" (list (car lxpsca) (cadr pbs)) "_h" "_non" (list (- (car pbs) 0) (- (cadr pbs) 200))
	    "_dimlinear" "_non" (list (car lxpsca) (cadr pbs)) "_non" pbd "_h" "_non" (list (- (car pbs) 0) (- (cadr pbs) 200))
	    )
    )
    (setq lxele nil)
  (setq lyele nil)
  (foreach n lpele
    (if (null (member (atof (rtos (car n) 2 1)) lxele)) (setq lxele (cons (atof (rtos (car n) 2 1)) lxele) ))
    (if (null (member (atof (rtos (cadr n) 2 1)) lyele)) (setq lyele (cons (atof (rtos (cadr n) 2 1)) lyele) ))
    )
(setq lxele (vl-sort lxele (function (lambda (e1 e2) (> e1 e2)))))
(setq lyele (vl-sort lyele (function (lambda (e1 e2) (> e1 e2)))))
(if lxele
  (progn
    (command"_dimlinear" "_non" pbs "_non" (setq ppa (list (last lxele) (cadr pbs))) "_h" "_non" (list (- (car pbs) 0) (+ (cadr pas) 200)))
    (foreach n (cdr (reverse lxele))
      (command"_dimlinear" "_non" ppa "_non" (setq ppa (list n (cadr pbs))) "_h" "_non" (list (- (car pbs) 0) (+ (cadr pas) 200)))
      )
    (command"_dimlinear" "_non" ppa "_non" (setq ppa pbd ) "_h" "_non" (list (- (car pbs) 0) (+ (cadr pas) 200)))
      
    )
  )
  (if lyele
  (progn
    (command"_dimlinear" "_non" pbd "_non" (setq ppa (list (car pbd) (last lyele))) "_v" "_non" (list (+ (car pbd) 100) (+ (cadr pas) 0)))
    (foreach n (cdr (reverse lyele))
      (command"_dimlinear" "_non" ppa "_non" (setq ppa (list (car pbd) n)) "_v" "_non" (list (+ (car pbd) 100) (+ (cadr pas) 0)))
      )
    (command"_dimlinear" "_non" ppa "_non" (setq ppa pas ) "_v" "_non" (list (+ (car pbd) 100) (+ (cadr pas) 0)))
      
    )
  )
      ;qui
  ;fronteoretro
  (if (= fronteoretro (substr (car pan) 1 2))
    (progn
      (command"_mirror" (ssget "x") "" "_non" (list (/ (+ (car pt) (car pt1)) 2) (cadr pt)) "_non" (list (/ (+ (car pt) (car pt1)) 2) (cadr pt2)) "_Yes")
      )
    )

  ;;;(command"_zoom" "_w" (list (- (car pp) 300) (- (cadr pp) 150)) (list (+ (car pp) 900) (+ (cadr pp) 2400)))
  (if (/= "D" mod)
    (progn
    (distbase_sv "no" (nth 0 pan) (list 1000 0 0) 0.3)
    (setq gri (ssget "x" (list '(0 . "INSERT") '(2 . "cartiglio"))))
    (setq intes (ssname gri 0))
    (setq ent (entnext intes))
    (setq entg (entget ent))
    (setq entn (subst (cons 1 (nth 0 pan)) (assoc '1 entg) entg))
    (entmod entn)
    (setq data (strcat (substr (rtos (getvar"cdate") 2 0) 7 2) "." (substr (rtos (getvar"cdate") 2 0) 5 2) "." (substr (rtos (getvar"cdate") 2 0) 3 2)))
     
    (setq ent (entnext ent))
    (setq entg (entget ent))
    (setq entn (subst (cons 1 data) (assoc '1 entg) entg))
    (entmod entn)
    
    (setq ent (entnext ent))
    (setq entg (entget ent))
    (setq entn (subst (cons 1 (strcat (nth 0 pan) )) (assoc '1 entg) entg))
    (entmod entn)
(setq ent (entnext ent))
    (setq entg (entget ent))
    (SETQ TITOLO "SVILUPPO LAMIERA")
    (setq entn (subst (cons 1 titolo) (assoc '1 entg) entg))
    (entmod entn)
    (ENTUPD INTES)
    ))
;;;  (alert "pippi")
  
;    pan
  (vl-file-delete (STRCAT (cadr (assoc 'perc_sviluppi parametri)) nompan ".dwg"))
;;;  (if (/= mod "D")
;;;    (progn
      (command"_layout" "_set" "A4")
      (command"_saveas" "2010" (STRCAT "\"" (cadr (assoc 'perc_sviluppi parametri)) nompan ".dwg\""))
;;;      (IF (> (GETVAR"CMDACTIVE") 0) (COMMAND"_y"))
  
(if close_t (command"_close"))
;;;      )
;;;    )
;;;;;;  (if (findfile (strcat (cadr (assoc 'perc_svi_dxf parametri)) nompan ".dxf"))
;;;        (command"_saveas" "dxf" "_v" "R12" 16 (strcat (cadr (assoc 'perc_svi_dxf parametri)) nompan) "_y")
;;;        (command"_saveas" "dxf" "_v" "R12" 16 (strcat (cadr (assoc 'perc_svi_dxf parametri)) nompan))
;;;    )
    (quote0-90)

)


(DEFUN c:NEWsvi ()
  (setq modalita (cadr (assoc 'percregtmp parametri)))
  (start)
  (prompt "\nSelezionare o Invio per disegnare solo i nuovi")
  (setq gr (ssget (list '(0 . "INSERT") '(2 . "codsvi*") '(8 . "siglepan"))))
  (if gr
    (progn
	  (setq nr 0)
	  (setq lisnom nil)
	  (setq 1gia nil)
	  (while (setq ent (ssname gr nr))
	    (setq nome (cdr (assoc '1 (entget (entnext ent)))))
	    (if (null (member nome lisnom)) (setq lisnom (cons nome lisnom)))
	    (IF (FINDFILE (STRCAT (cadr (assoc 'perc_sviluppi parametri)) NOME ".DWG")) (setq 1gia "t"))
	    (setq nr (+ 1 nr))
	  )
	  (if 1gia
	    (progn
	      (INITGET "Si No")
	      (setq sn (getkword "\nSviluppo già disegnato lo ridisegno [No/Si]:"))
	    )
	    (setq sn "Si")
	  )
    )
    (progn
      (setq lisnom $sviluppi)
      (setq $sviluppi nil)
      (if (null lisnom) (progn (alert "Niente di nuovo") (exit)))
      (setq sn "Si")
    )
  )
  (setq lisnom_ nil)
  (foreach n lisnom
    (if (null (member n lisnom_))
      (setq lisnom_ (cons n lisnom_))
      )
    )
  (setq lisnom lisnom_)
    
  (if (= sn "Si")
    (progn
        (SETQ FILE (OPEN (strcat "c:\\ACAD_TMP\\newpan.SCR") "W"))
          (WRITE-LINE (strcat "_NEW " "sviluppo") FILE)
          (WRITE-LINE "(LOAD\"ACAD\")" FILE)
      (write-line "_setvar tilemode 1" file)
;;;       (foreach nome lisnom
;;;          (vl-file-delete (STRCAT (cadr (assoc 'perc_sviluppi parametri)) NOME ".dwg"))
;;; 	  (write-line "_setvar tilemode 1" file)
;;;          (WRITE-LINE (STRCAT "DISsvi " NOME " t" ) FILE)
;;;          (WRITE-LINE (STRCAT "_LAYOUT _SET A4 _SAVEAS 2013 "(cadr (assoc 'perc_sviluppi parametri)) NOME) FILE)
;;;        )
;;;        (write-line "_close" file)
;;;
          (WRITE-LINE (STRCAT "DISsvi_g") FILE)
      (SETQ FILEt (OPEN (strcat "c:\\ACAD_TMP\\newpan.txt") "W"))
      (write-line "(setq liss '(" filet)
       (foreach nome lisnom
          (vl-file-delete (STRCAT (cadr (assoc 'perc_sviluppi parametri)) NOME ".dwg"))
 	  
          (WRITE-LINE (STRCAT "\"" NOME "\" ") FILEt)
        )
      (write-line "))" filet)
;;;        (write-line "_close" file)
        (CLOSE FILE)
        (CLOSE FILEt)
        (COMMAND "SCRIPT" "c:\\ACAD_TMP\\newPAN")
    )
  )
  (stop)
)

(defun c:dissvi_g ()
  (load"c:\\acad_tmp\\newpan.txt")
  (setq modalita (cadr (assoc 'percregtmp parametri)))

  (foreach nomepan liss
  (dissvi nomepan "n")
    (setvar "tilemode" 1)
    
    )
    (command"_close" "_n")

  )

(defun distbase_sv (testa assieme pt scala)
;;;  (command"_undo" "_g")
  (setq listad nil)
  (setq pos 0)
  (setq rigedist nil)
  (if (null rigedist)
    (progn
  (setq rigedist (carica "anag" ""))
  (if (findfile (strcat modalita "$$sviluppi" ".txt"))
    (setq file (open (findfile (strcat modalita "$$sviluppi" ".txt")) "r"))
    (setq file (open (findfile (strcat modalita "sviluppi" ".txt")) "r"))
    )
  (while (setq r (read-line file))
    (setq r (read (strcat "(" r ")")))
    (setq rigedist (cons (list (nth 0 r) (nth 10 r) (nth 1 r)) rigedist))
  )
  (close file)
  (if (findfile (strcat modalita "$$sviluppi_r" ".txt"))
    (setq file (open (findfile (strcat modalita "$$sviluppi_R" ".txt")) "r"))
    (setq file (open (findfile (strcat modalita "sviluppi_R" ".txt")) "r"))
    )
  (while (setq r (read-line file))
    (setq r (read (strcat "(" r ")")))
    (setq rigedist (cons (list (nth 0 r) (nth 10 r) (nth 1 r)) rigedist))
  )
  (close file)

  (setq file (open (findfile (strcat modalita "cesoiati" ".txt")) "r"))
  (while (setq r (read-line file))
    (setq r (read (strcat "(" r ")")))
    (setq rigedist (cons (list (nth 0 r) (nth 7 r) (nth 1 r)) rigedist))
  )
  (close file)
  (setq file (open (findfile (strcat modalita "cesoiati_r" ".txt")) "r"))
  (while (setq r (read-line file))
    (setq r (read (strcat "(" r ")")))
    (setq rigedist (cons (list (nth 0 r) (nth 7 r) (nth 1 r)) rigedist))
  )
  (close file)

  (if (null distsvi) (setq distsvi (carica_f "dibsvi" modalita)))
  (foreach n distsvi
   (if (and (and (/= "000000000" (cadr n)) (/= "000000001" (cadr n)) (/= "000000002" (cadr n))) (= assieme (car n)))
    
     (if (null (assoc (cadr n) rigedist)) (alert (strcat "Codice " (cadr n) " non in anarafica !!!2" ))
       (setq listad
         (cons
            (list (cadr n) (nth 2 (assoc (cadr n) rigedist)) (nth 1 (assoc (cadr n) rigedist)) (rtos (/ (nth 7 n) 1.0) 2 2))
            listad
         )
      )
     )
    )
  )
  (if (null distsvi_r) (setq distsvi_R (carica_f "dibsvi_r" modalita)))
  (foreach n distsvi_R
   (if (and (and (/= "000000000" (cadr n)) (/= "000000001" (cadr n)) (/= "000000002" (cadr n))) (= assieme (car n)))
    
     (if (null (assoc (cadr n) rigedist)) (alert (strcat "Codice " (cadr n) " non in anarafica !!!2" ))
       (setq listad
         (cons
            (list (cadr n) (nth 2 (assoc (cadr n) rigedist)) (nth 1 (assoc (cadr n) rigedist)) (rtos (/ (nth 7 n) 1.0) 2 2))
            listad
         )
      )
     )
    )
  )
    )
  )
  (setvar"expert" 5)
  
  (if (= testa "si")
    (progn
      (COMMAND"_INSERT" "testatab" "_non" pt scala scala "0" assieme (nth 2 (assoc assieme rigedist)))
      (command"_-group" "_c" (substr assieme 2 2) "" (entlast) "")
    )
    (command"_-group" "_c" (substr assieme 2 2) "" "")
  )
  (setvar"expert" 1)
  (setq listam listad)
  (setq listad nil)
  (foreach n listam
    (if (assoc (car n) listad)
      (setq listad
	     (subst (list (nth 0 n) (nth 1 n) (nth 2 n) (rtos (+ (atof (nth 3 n)) (atof (nth 3 (assoc (car n) listad)))) 2 2))
		    (assoc (car n) listad)
		    listad
	     )
      )
      (setq listad (cons n listad))
    )
  )
  (foreach n listad
      (COMMAND"_INSERT" "rigatab" "_non" pt scala scala "0")
      (cond ((= "MQ" (strcase (nth 2 n)))
             (command (rtos (setq pos (+ 1 pos)) 2 0) (nth 0 n) (nth 1 n) (nth 2 n) (rtos (/ (atof (nth 3 n)) 1000000)2 2))
	    )
	    ((= "ML" (strcase (nth 2 n)))
             (command (rtos (setq pos (+ 1 pos)) 2 0) (nth 0 n) (nth 1 n) (nth 2 n) (rtos (/ (atof (nth 3 n)) 1000)2 2))
	    )
	    ((= "KG" (strcase (nth 2 n)))
             (command (rtos (setq pos (+ 1 pos)) 2 0) (nth 0 n) (nth 1 n) (nth 2 n) (rtos (/ (atof (nth 3 n)) 1000)2 2))
	    )
	    ("t"
             (command (rtos (setq pos (+ 1 pos)) 2 0) (nth 0 n) (nth 1 n) (nth 2 n) (rtos (/ (atof (nth 3 n)) 1)2 0))
	    )
      )
      (if (= testa "si") (command"_-group" "_add" (substr assieme 2 2) (entlast) ""))
    (setq pt (list (car pt) (- (cadr pt) (* scala 100) 0)))
  )
;  (command"_undo" "_e")
  (setq $pt$ pt)
)
