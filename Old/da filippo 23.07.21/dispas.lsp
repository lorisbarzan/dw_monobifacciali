;Rev 2020
(defun c:dispaS ()
  (setq prk t)
  (IF (/= MODALITA (cadr (assoc 'percregtmp parametri))) (C:ANNTAB))
  (setq modalita (cadr (assoc 'percregtmp parametri)))
  (setq modalitac (cadr (assoc 'percregcom parametri)))
  (start)
  (setq nompan (getstring "\nCodice pannello <+24PN00002>"))
  (if (= "" nompan) (setq nompan "+00PN22427"))
;;;  (setq *error* nil)
  (dispas nompan "n")
  (stop)
)

(defun dispas (nomepan modo)
  (dispas_n nomepan modo 0 0 0)
  )

(defun dispaS_n (nompan modo angk modo_old y_s)
  (setq *error* nil)
  (SETQ  LISPTRV NIL)
  (setq d220 nil)
  	  (setq tipomb "Monofacciale")

  (setq elet "No")
(COMMAND "_COLOR" "bylayer")
  (setq PRESE (carica "PRESE" ""))
  (setq scatoleinkit nil)
(setq lpqscatole nil)
  (foreach n prese (setq scatoleinkit (cons (nth 1 n) scatoleinkit)) )
     (setq npres $tb$)
  (setq angktmp (angtos angk))
  (if (= modo_old "S")
    (setq pp_s pp pik_s pik ulta_s ulta angk1_s angk1 angk_s angk)
  )
  
  (if (= modo "D") (progn 
		     (setq entblocco (entlast))
		         
))
  (IF (/= modo "D")
      (if (/= modo "k")  (command "_erase" "_all" ""))
    )
;;;  (setq *error* nil)
  (if (OR (= modo "l") (= modo "D"))
    (setq lispan_g (read (strcat "(" (leggi entpan "pannellil") ")")))
    (if (null lispan_g) (setq lispan_g (carica_f "pannellil" modalita)))
  )

    (if (OR (= modo "l") (= modo "D"))
       (setq lispas_g (read (strcat "(" (leggi entpan "pannelli") ")")))
       (if (null lispaS_g) (setq lispaS_g (carica_f "pannelli" modalita)))
      )

  (if (null prese) (setq prese (carica "prese" "")))
  (if (null rinforzi)(progn  (setq rinforzi (carica "rinforzi" ""))(setq rinforz $tb$) ))
  (SETQ NOMpas nompan)
  (setq nompan (nth 1 (assoc nompas lispas_g)))
  (SETQ TIPOPAN (nth 10 (assoc nompas lispas_g)))
  (setq modop_d (nth 10 (assoc nompas lispas_g)))
  (setq pan (assoc nompan lispan_g))
  (if (/= 0 (nth 3 pan)) (setq cart_ang "P") (setq cart_ang ""))
  (if (/= "No" (nth 8 pan)) (setq cart_for "F") (setq cart_for ""))
  (setq cart_rinf "")
  
  (setq pprifk pp)
  (if (= modo "k")
  (if (= 0 angk)
    (progn
      (setq pp (polar pp 0 (nth 2 pan)))
      (setq pik (+ angk pi))
      (setq ulta nil)
    )
    (progn 
      (setq pp (polar pp 0 (nth 3 pan)))
      (setq angk1 (- (* 3 pi) angk))
      (setq pp (polar pp 0 (nth 2 pan)))
      (setq pik (- angk1 pi))
      (setq angk (- pi angk))
      (setq ulta "T")
    )
  )
    )
  
  (if (= 0 (nth 3 pan)) (setq pandri "t" PANANG NIL) (setq pandri nil PANANG "T"))
  (setq angpan (* (/ (nth 6 pan) 180.0) pi))
  (if (null pan) (progn (alert "Pannello inesistente !!!") (exit)))
  (setq fpan "STD")
  (setq scver 1)
  (if (= modo "n")
(IF (AND PANANG
	   (> (NTH 6 PAN) 180)
      )
      (setq pp (polar (list 0 300 0) 0 0))
      (setq pp (polar (list 0 0 0) 0 0))
  )
    )
  (if (= modo "D") (SETQ pp (GETPOINT "\nPunto di inserimnto:")))
  (setq pp_rif pp)
  (IF (NOT (= modo "k"))
    (progn
  (IF (AND PANANG
	   (> (NTH 6 PAN) 180)
      )
      (if (or (= modo "n") (= modo "k")) (setq pp pp) (setq pp (polar (list (car pp) (+ (cadr pp) 300) 0) 0 0)))
      (if (or (= modo "n") (= modo "k")) (setq pp pp) (setq pp (polar (list (car pp) (- (cadr pp) 400) 0) 0 0)))
  )
  (IF (AND PANDRI)
      (if (or (= modo "n") (= modo "k")) (setq pp pp) (setq pp (polar (list (- (car pp) 0) (- (cadr pp) 250) 0) 0 0)))
  )
  )
       
    )
  (setq pp_x_k pp)
  (if (AND (< ANGPAN PI) (= modo "k")) (setq angpan 0))
  (IF (and (= angk 0) (= MODO "k")) (setq angpan (* (/ (nth 6 pan) 180.0) pi)) (if (= modo "k") (setq angpan 0)))
  
  (if pandri
    (cond ((= "STD" (nth 11 pan)) (pannellon PP (setq pp1 (polar PP pi (nth 2 pan))) (nth 4 pan)))
	  ((= "SPC" (nth 11 pan)) (pannellosd PP (setq pp1 (polar PP pi (nth 2 pan))) (nth 4 pan)))
	  ((= "SPM" (nth 11 pan)) (pannelloM PP (setq pp1 (polar PP pi (nth 2 pan))) (nth 4 pan)))
	  ((= "MAN" (nth 11 pan)) (pannello_x PP (setq pp1 (polar PP pi (nth 2 pan))) (nth 4 pan)))
	  ((= "MPM" (nth 11 pan)) (pannelloM PP (setq pp1 (polar PP pi (nth 2 pan))) (nth 4 pan)))
	  ((= "MTD" (nth 11 pan)) (pannellon PP (setq pp1 (polar PP pi (nth 2 pan))) (nth 4 pan)))
	  ((= "MPC" (nth 11 pan)) (pannellosd PP (setq pp1 (polar PP pi (nth 2 pan))) (nth 4 pan)))

)
        ;AGG GIUGNO

    (cond ((= "STD" (nth 11 pan)) (angolon PP (setq pp1 (polar PP pi (nth 2 pan))) (setq ppa2 (polar pp1 (+ angk angpan) (nth 3 pan))) (nth 4 pan)))
	  ((= "SPC" (nth 11 pan)) (angolosd PP (setq pp1 (polar PP pi (nth 2 pan))) (setq ppa2 (polar pp1 (+ angk angpan) (nth 3 pan))) (nth 4 pan)))
	  ((= "SPM" (nth 11 pan)) (angoloM PP (setq pp1 (polar PP pi (nth 2 pan))) (setq ppa2 (polar pp1 (+ angk angpan) (nth 3 pan))) (nth 4 pan)))
	  ((= "MAN" (nth 11 pan)) (angolo_X PP (setq pp1 (polar PP pi (nth 2 pan))) (nth 4 pan)))
          ((= "MTD" (nth 11 pan)) (angolon PP (setq pp1 (polar PP pi (nth 2 pan))) (setq ppa2 (polar pp1 (+ angk angpan) (nth 3 pan))) (nth 4 pan)))
	  ((= "MPC" (nth 11 pan)) (angolosd PP (setq pp1 (polar PP pi (nth 2 pan))) (setq ppa2 (polar pp1 (+ angk angpan) (nth 3 pan))) (nth 4 pan)))
	  ((= "MPM" (nth 11 pan)) (angoloM PP (setq pp1 (polar PP pi (nth 2 pan))) (setq ppa2 (polar pp1 (+ angk angpan) (nth 3 pan))) (nth 4 pan)))

  )
  )
(vai_l "0")
  (setq panpianta (entlast))

;;;   Disegnata pianta

  

  
  (command "_chprop" (entlast) "" "_co" "bylayer" "")
(command "_COLOR" "bylayer")
  (setq pp1_qr pp1)
  (setq entlastg (entlast))
    (if panang
      (if (> angpan pi)
	(command "_INSERT" "DEM220$" "_NON" ppa2 "1" "1" "90")
	(command "_INSERT" "DEM220$" "_NON" ppa2 "1" "1" "270")
	)
      (command "_INSERT" "DEM220$" "_NON" pp1 "1" "1" "0"))
  (SETQ ENTLAST220 (ENTLAST))
  (setq pp220 pp1)
  (if panang (setq pp220 ppa1))
  (IF PANANG
    (PROGN
      (IF (> (DISTANCE PP PP1) (DISTANCE PP1 PPA2))
	(PROGN
          (command "_MOVE" ENTLASTPAN entlastg ENTLAST220 "" "_NON" (SETQ PPM1 PP) "_NON" (SETQ PPM PP1))
	  (SETQ P1_R (CDR (ASSOC '10 (ENTGET ENTLASTPAN))))
	  (SETQ P2_R (CDR (ASSOC '10 (SETQ LS_R (CDR (MEMBER (ASSOC '10 (ENTGET ENTLASTPAN)) (ENTGET ENTLASTPAN)))))))
	  (SETQ P3_R (CDR (ASSOC '10 (CDR (MEMBER (ASSOC '10 LS_R) LS_R)))))
          (COMMAND "_ROTATE" ENTLASTPAN entlastg ENTLAST220 "" "_NON" PPM "_R" "_NON" PPM "_NON" PPM1 "180")
	  (SETQ P1_R (CDR (ASSOC '10 (ENTGET ENTLASTPAN))))
	  (SETQ P2_R (CDR (ASSOC '10 (SETQ LS_R (CDR (MEMBER (ASSOC '10 (ENTGET ENTLASTPAN)) (ENTGET ENTLASTPAN)))))))
	  (SETQ P3_R (CDR (ASSOC '10 (CDR (MEMBER (ASSOC '10 LS_R) LS_R)))))
          (setq pm_r (polar p1_r (angle p1_r p2_r) (/ (distance p1_r p2_r) 2)))
         (SETQ A 1)
	  )
	(PROGN
          (COMMAND "_ROTATE" ENTLASTPAN entlastg ENTLAST220 "" "_NON" pp1 "_R" "_NON" pp1 "_NON" ppa2 "0")
	  (SETQ P1_R (CDR (ASSOC '10 (ENTGET ENTLASTPAN))))
	  (SETQ P2_R (CDR (ASSOC '10 (SETQ LS_R (CDR (MEMBER (ASSOC '10 (ENTGET ENTLASTPAN)) (ENTGET ENTLASTPAN)))))))
	  (SETQ P3_R (CDR (ASSOC '10 (CDR (MEMBER (ASSOC '10 LS_R) LS_R)))))
 	  (command "_MOVE" ENTLASTPAN entlastg ENTLAST220 "" "_NON" p3_r "_NON" p2_r)
	  (SETQ P1_R (CDR (ASSOC '10 (ENTGET ENTLASTPAN))))
	  (SETQ P2_R (CDR (ASSOC '10 (SETQ LS_R (CDR (MEMBER (ASSOC '10 (ENTGET ENTLASTPAN)) (ENTGET ENTLASTPAN)))))))
	  (SETQ P3_R (CDR (ASSOC '10 (CDR (MEMBER (ASSOC '10 LS_R) LS_R)))))
          (setq pm_r (polar p2_r (angle p2_r p3_r) (/ (distance p2_r p3_r) 2)))
         (SETQ A 1)
	  )
	)
      
      )
    (PROGN
      (command "_MOVE" ENTLASTPAN entlastg ENTLAST220 "" "_NON" (SETQ PPM1 PP) "_NON" (SETQ PPM PP1))
      (COMMAND "_ROTATE" ENTLASTPAN entlastg ENTLAST220 "" "_NON" PPM "_R" "_NON" PPM "_NON" PPM1 "180")
      	  (SETQ P1_R (CDR (ASSOC '10 (ENTGET ENTLASTPAN))))
	  (SETQ P2_R (CDR (ASSOC '10 (SETQ LS_R (CDR (MEMBER (ASSOC '10 (ENTGET ENTLASTPAN)) (ENTGET ENTLASTPAN)))))))
	  (SETQ P3_R nil)
          (setq pm_r (polar p2_r (angle p2_r p1_r) (/ (distance p2_r p1_r) 2)))
      )
    )
;;;  (if (and panang t)
;;;    (if (< (NTH 6 PAN) 180)
;;;    (progn
;;;       (command "_rotate" entlastpan entlastg (entlast) "" "_non" pp1 90)
;;;       (setq entg (entget entlastpan))
;;;      (setq pp_qr (cdr (assoc '10 entg)))
;;;      (setq pp1_qr (cdr (assoc '10 (setq entg1 (cdr (member (assoc '10 entg) entg))))))
;;;      (setq ppa2_qr (cdr (assoc '10 (cdr (member (assoc '10 entg1) entg1)))))
;;;      
;;;      )
;;;      (progn
;;;       (command "_rotate" entlastpan "" "_non" pp1 -90)
;;;       (if (/= modo "k") (command "_move" entlastpan entlastg (entlast) "" "_non" '(0 0 0) "_non" '(0 -900 0)))
;;;       (setq entg (entget entlastpan))
;;;      (setq pp_qr (cdr (assoc '10 entg)))
;;;      (setq pp1_qr (cdr (assoc '10 (setq entg1 (cdr (member (assoc '10 entg) entg))))))
;;;      (setq ppa2_qr (cdr (assoc '10 (cdr (member (assoc '10 entg1) entg1)))))
;;;      
;;;      )
;;;    )
;;;    (progn
;;;            (setq pp_qr pp)
;;;      (setq pp1_qr pp1)
;;;      (setq ppa2_qr ppa2)
;;;
;;;      )
;;;    )
 (vai_l "0")
    (if (= modo "k") (setq pt (setq pprifk pp)))
  (if (= modo "D") (command "_layer" "_m" "Pan_assieme" ""))
  (if (= modo "D") (command "_chprop" entlastpan "" "_la" "Pan_assieme" ""))
  (if (/= modo "k") (if pp_rif (setq pp pp_rif)))
  (setq copip entlastpan)
    (setq ppul pp)
  (if ulta
    (setq pp pp)
  )

    (setq pt (list (CAR PP) (+ (cadr pp) 0) 0))

  (setq pp_rif pp)
  (if (= modo "n") (setq y_s 500))
  (setq y_S (+ (cadr pt) y_S))
  (command "_pline" "_non" (setq pt (list (CAR PP) y_S 0))
	    "_non" (SETQ P220 (setq pt1 (polar pt pi (nth 2 pan))))
	    "_non" (setq pt2 (polar pt1 (/ pi 2) (* scver (nth 5 pan))))
	    "_non" (setq pt3 (polar pt2 0 (nth 2 pan)))
	    "_c"
  )
  (if (= modo "D") (progn 
		     		           (command "_point" "_non" pt)
        (allega (entlast) "pan" (cdr (assoc '5 (entget entpan))))
))
  (IF PANANG
    (progn
      (command "_pline" "_non" (setq pA (list (- (CAR pt) (NTH 2 PAN) ) y_s 0))
 	    "_non" (SETQ P220 (setq pA1 (polar pA pi (nth 3 pan))))
	    "_non" (setq pA2 (polar pA1 (/ pi 2) (* scver (nth 5 pan))))
	    "_non" (setq pA3 (polar pA2 0 (nth 3 pan)))
	    "_c"
      )
    )
	      
  )
  (IF (NULL PINQT)
    (IF PANANG (SETQ PINQT PA pinqtd pa1 PFIQTd pt) (SETQ PINQT PT1 pinqtd PT1))
  )
  (IF PANDRI (setq pqfV PT1) (SETQ PQFV PA1))
  (setq pqrv PT)
  (setq pqfh1 PT)
  (setq pqfh2 PT)
  (command "_dim1" "_res" "PANNELLI")
;;;  (if (/= modo "kk") (command "_dimaligned" "_non" pp_qr "_non" pp1_qr "_non" (polar pp_qr (- (angle pp_qr pp1_qr) (/ pi 2)) 70)))
  (if (/= modo "kk") (command "_dimaligned" "_non" p1_r "_non" p2_r "_non" (polar p2_r  (- (angle p1_r p2_r) (/ pi 2)) 70)))
  (if (/= modo "k") (command "_dimlinear" "_non" pT3 "_non" pT2 "_H" "_non" (polar pt3 (* 1 (/ pi 2)) 70)))
  (if panang (if (/= modo "k") (command "_dimlinear" "_non" pa3 "_non" pA2 "_H" "_non" (polar pa3 (* 1 (/ pi 2)) 70))))
  (if panang (if (/= modo "kk") (command "_dimaligned" "_non" p2_r "_non" p3_r "_non" (polar p2_r (- (angle p2_r p3_r) (/ pi 2)) 70))))
  (if panang (if (/= modo "kk") (command "_dimANGULAR" "" "_non" p2_r "_non" p1_r "_non" p3_r  "_non" (polar p2_r (- (angle p2_r p3_r) (/ pi 2)) 190))))
  
;;;  (if (/= modo "k") (command "_dimaligned" "_non" pp_qr "_non" (polar pp_qr (+ (angle pp_qr pp1_qr) (/ pi 2)) (nth 4 pan)) "_non" (polar pp_qr (+ pi (angle pp_qr pp1_qr)) 50)))
  (setvar "dimlfac" (/ 1 scver))
  (IF PANANG
      (if (/= modo "k") (command "_dimlinear" "_non" pA1 "_non" pA2 "_V" "_non" (polar pA1 pi 200)))
      (if (/= modo "k") (command "_dimlinear" "_non" pt1 "_non" pt2 "_V" "_non" (polar pt1 pi 200)))
  )
  (setvar "dimlfac" 1)
  (if (NOT (OR (= modo "l") (= modo "D")))
    (if (null distpan) (setq distpan (carica_f "dibpan" modalita)))
    (progn
       (setq distpan_ (read (strcat "(" (leggi entpan "dibpan") ")")))
       (setq distpan nil)
       (foreach n distpan_
          (setq distpan (cons (list (nth 0 n) (nth 1 n) (nth 5 n) (nth 6 n) (nth 7 n) (nth 8 n) (nth 9 n)) distpan))
       )
      )
    )
    (setq carter nil)
;;;  (alert (strcat "disegno carter ???" nompas))
  (if (null distpaS)
  (setq distpaS (carica_f "dibpaS" modalita)))
  (setq memb distpaS)
      (if (null lispan_g_r)
	(setq lispan_g_r (carica_f "pannellil_r" modalita)))
  (while (setq memb (member (assoc nompas (cdr memb)) (cdr memb)))
     (print (car memb))
    (if (setq tmp (assoc (cadr (car memb)) lispan_g_r)) 
        (progn
	  (allega panpianta "TIPOMB" "Bifacciale")
	  (setq tipomb "Bifacciale")
	  (if (or (= "CVS" (nth 11 tmp)) (= "CVD" (nth 11 tmp)) (= "COR" (nth 11 tmp)) (= "CAS" (nth 11 tmp)) (= "CAD" (nth 11 tmp)))
	    (progn (setq carter tmp carter_p (car  memb))
	      (allega panpianta "CARTER" (strcat (nth 11 carter) (rtos (nth 2 carter))))
	      )
	    )
	  )
      )
    )

  
(setq pr nil)
  
  (if carter
    (progn
      (vai_l "pan_carter")
;;;(alert "disegno carter")

      (if (= "CAS" (nth 11 carter))
  (progn
	(command "_pline" "_non" (setq ptc (list (+ (CAR pt) (nth 6 carter_p)) (+ y_s (nth 7 carter_p)) 0))
		    "_non" (setq pt1c (polar ptc pi (- (nth 2 carter) 36)))
		    "_non" (setq pt2c (polar pt1c (/ pi 2) (* scver (nth 5 carter))))
		    "_non" (setq pt3c (polar pt2c 0 (- (nth 2 carter) 36)))
		    "_c"
	  )
    (command "_pline" "_non" (setq ptc (list (+(- (+ (CAR pt)  (nth 6 carter_p)) (nth 2 carter))36)(+ y_s (nth 7 carter_p)) 0))
		    "_non" (setq pt1c (polar ptc pi 20))
		    "_non" (setq pt2c (polar pt1c (/ pi 2) (* scver (nth 5 carter))))
		    "_non" (setq pt3c (polar pt2c 0 20))
		    "_c"
	  )
    (command "_pline" "_non" (setq ptc (list (+(- (- (+ (CAR pt)  (nth 6 carter_p)) (nth 2 carter)) 20)36)(+ y_s (nth 7 carter_p)) 0))
		    "_non" (setq pt1c (polar ptc pi 19.3))
		    "_non" (setq pt2c (polar pt1c (/ pi 2) (* scver (nth 5 carter))))
		    "_non" (setq pt3c (polar pt2c 0 19.3))
		    "_c"
	    )
    (progn
      (command "_circle" "_non" (list (+ (car pt1c)  10) (- (+ (cadr ptc) (/ (nth 5 carter) 2)) 150)) 2.5)
      (command "_circle" "_non" (list (+ (car pt1c)  10) (- (+ (cadr ptc) (/ (nth 5 carter) 2)) 450)) 2.5)
      (command "_circle" "_non" (list (+ (car pt1c)  10) (+ (+ (cadr ptc) (/ (nth 5 carter) 2)) 150)) 2.5)
      (command "_circle" "_non" (list (+ (car pt1c)  10) (+ (+ (cadr ptc) (/ (nth 5 carter) 2)) 450)) 2.5)
(if (> (nth 5 carter) 1600)
  (progn
      (command "_circle" "_non" (list (+ (car pt1c)  10) (- (+ (cadr ptc) (/ (nth 5 carter) 2)) 750)) 2.5)
      (command "_circle" "_non" (list (+ (car pt1c)  10) (+ (+ (cadr ptc) (/ (nth 5 carter) 2)) 750)) 2.5)
    )
  )
      (if (> (nth 5 carter) 2109)
  (progn

      (command "_circle" "_non" (list (+ (car pt1c)  10) (- (+ (cadr ptc) (/ (nth 5 carter) 2)) 1050)) 2.5)
      (command "_circle" "_non" (list (+ (car pt1c)  10) (+ (+ (cadr ptc) (/ (nth 5 carter) 2)) 1050)) 2.5)
    ))
      )
    )
  )

      (if (= "CAD" (nth 11 carter))
  (progn
	(command "_pline" "_non" (setq ptc (list (- (CAR pt) (nth 6 carter_p)) (+ y_s (nth 7 carter_p)) 0))
		    "_non" (setq pt1c (polar ptc 0 (- (nth 2 carter) 36)))
		    "_non" (setq pt2c (polar pt1c (/ pi 2) (* scver (nth 5 carter))))
		    "_non" (setq pt3c (polar pt2c pi (- (nth 2 carter) 36)))
		    "_c"
	  )
    (command "_pline" "_non" (setq ptc (list (-(+ (nth 2 carter) (- (CAR pt)  (nth 6 carter_p)))36) (+ y_s (nth 7 carter_p)) 0))
		    "_non" (setq pt1c (polar ptc 0 20))
		    "_non" (setq pt2c (polar pt1c (/ pi 2) (* scver (nth 5 carter))))
		    "_non" (setq pt3c (polar pt2c pi 20))
		    "_c"
	  )
    (command "_pline" "_non" (setq ptc (list (-(+ (+ (nth 2 carter) (- (CAR pt)  (nth 6 carter_p))) 20)36) (+ y_s (nth 7 carter_p)) 0))
		    "_non" (setq pt1c (polar ptc 0 19.3))
		    "_non" (setq pt2c (polar pt1c (/ pi 2) (* scver (nth 5 carter))))
		    "_non" (setq pt3c (polar pt2c pi 19.3))
		    "_c"
	  )
    (progn
      (command "_circle" "_non" (list (- (car pt1c)  10) (- (+ (cadr ptc) (/ (nth 5 carter) 2)) 150)) 2.5)
      (command "_circle" "_non" (list (- (car pt1c)  10) (- (+ (cadr ptc) (/ (nth 5 carter) 2)) 450)) 2.5)
      (command "_circle" "_non" (list (- (car pt1c)  10) (+ (+ (cadr ptc) (/ (nth 5 carter) 2)) 150)) 2.5)
      (command "_circle" "_non" (list (- (car pt1c)  10) (+ (+ (cadr ptc) (/ (nth 5 carter) 2)) 450)) 2.5)
(if (> (nth 5 carter) 1600)
  (progn
      (command "_circle" "_non" (list (- (car pt1c)  10) (- (+ (cadr ptc) (/ (nth 5 carter) 2)) 750)) 2.5)
      (command "_circle" "_non" (list (- (car pt1c)  10) (+ (+ (cadr ptc) (/ (nth 5 carter) 2)) 750)) 2.5)
    )
  )
      (if (> (nth 5 carter) 2109)
  (progn

      (command "_circle" "_non" (list (- (car pt1c)  10) (- (+ (cadr ptc) (/ (nth 5 carter) 2)) 1050)) 2.5)
      (command "_circle" "_non" (list (- (car pt1c)  10) (+ (+ (cadr ptc) (/ (nth 5 carter) 2)) 1050)) 2.5)
    ))
      )
    )
  )
      
(if (= "CVS" (nth 11 carter))
  (progn
	(command "_pline" "_non" (setq ptc (list (+ (CAR pt) (nth 6 carter_p)) (+ y_s (nth 7 carter_p)) 0))
		    "_non" (setq pt1c (polar ptc pi (nth 2 carter)))
		    "_non" (setq pt2c (polar pt1c (/ pi 2) (* scver (nth 5 carter))))
		    "_non" (setq pt3c (polar pt2c 0 (nth 2 carter)))
		    "_c"
	  )
    (command "_pline" "_non" (setq ptc (list (- (+ (CAR pt)  (nth 6 carter_p)) (nth 2 carter))(+ y_s (nth 7 carter_p)) 0))
		    "_non" (setq pt1c (polar ptc pi 20))
		    "_non" (setq pt2c (polar pt1c (/ pi 2) (* scver (nth 5 carter))))
		    "_non" (setq pt3c (polar pt2c 0 20))
		    "_c"
	    )
    (progn
      (command "_circle" "_non" (list (+ (car pt1c)  10) (- (+ (cadr ptc) (/ (nth 5 carter) 2)) 150)) 2.5)
      (command "_circle" "_non" (list (+ (car pt1c)  10) (- (+ (cadr ptc) (/ (nth 5 carter) 2)) 450)) 2.5)
      (command "_circle" "_non" (list (+ (car pt1c)  10) (+ (+ (cadr ptc) (/ (nth 5 carter) 2)) 150)) 2.5)
      (command "_circle" "_non" (list (+ (car pt1c)  10) (+ (+ (cadr ptc) (/ (nth 5 carter) 2)) 450)) 2.5)
(if (> (nth 5 carter) 1600)
  (progn
      (command "_circle" "_non" (list (+ (car pt1c)  10) (- (+ (cadr ptc) (/ (nth 5 carter) 2)) 750)) 2.5)
      (command "_circle" "_non" (list (+ (car pt1c)  10) (+ (+ (cadr ptc) (/ (nth 5 carter) 2)) 750)) 2.5)
    )
  )
      (if (> (nth 5 carter) 2109)
  (progn

      (command "_circle" "_non" (list (+ (car pt1c)  10) (- (+ (cadr ptc) (/ (nth 5 carter) 2)) 1050)) 2.5)
      (command "_circle" "_non" (list (+ (car pt1c)  10) (+ (+ (cadr ptc) (/ (nth 5 carter) 2)) 1050)) 2.5)
    ))
      )
    )
  )
(if (= "CVD" (nth 11 carter))
  (progn
	(command "_pline" "_non" (setq ptc (list (- (CAR pt) (nth 6 carter_p)) (+ y_s (nth 7 carter_p)) 0))
		    "_non" (setq pt1c (polar ptc 0 (nth 2 carter)))
		    "_non" (setq pt2c (polar pt1c (/ pi 2) (* scver (nth 5 carter))))
		    "_non" (setq pt3c (polar pt2c pi (nth 2 carter)))
		    "_c"
	  )
    (command "_pline" "_non" (setq ptc (list (+ (nth 2 carter) (- (CAR pt)  (nth 6 carter_p))) (+ y_s (nth 7 carter_p)) 0))
		    "_non" (setq pt1c (polar ptc 0 19.3))
		    "_non" (setq pt2c (polar pt1c (/ pi 2) (* scver (nth 5 carter))))
		    "_non" (setq pt3c (polar pt2c pi 19.3))
		    "_c"
	  )
    (progn
      (command "_circle" "_non" (list (- (car pt1c)  10) (- (+ (cadr ptc) (/ (nth 5 carter) 2)) 150)) 2.5)
      (command "_circle" "_non" (list (- (car pt1c)  10) (- (+ (cadr ptc) (/ (nth 5 carter) 2)) 450)) 2.5)
      (command "_circle" "_non" (list (- (car pt1c)  10) (+ (+ (cadr ptc) (/ (nth 5 carter) 2)) 150)) 2.5)
      (command "_circle" "_non" (list (- (car pt1c)  10) (+ (+ (cadr ptc) (/ (nth 5 carter) 2)) 450)) 2.5)
(if (> (nth 5 carter) 1600)
  (progn
      (command "_circle" "_non" (list (- (car pt1c)  10) (- (+ (cadr ptc) (/ (nth 5 carter) 2)) 750)) 2.5)
      (command "_circle" "_non" (list (- (car pt1c)  10) (+ (+ (cadr ptc) (/ (nth 5 carter) 2)) 750)) 2.5)
    )
  )
      (if (> (nth 5 carter) 2109)
  (progn

      (command "_circle" "_non" (list (- (car pt1c)  10) (- (+ (cadr ptc) (/ (nth 5 carter) 2)) 1050)) 2.5)
      (command "_circle" "_non" (list (- (car pt1c)  10) (+ (+ (cadr ptc) (/ (nth 5 carter) 2)) 1050)) 2.5)
    ))
      )
    )
  )
(if (= "COR" (nth 11 carter))
  (progn
    (command "_pline" "_non" (setq ptc (list (+ (CAR pt) (nth 6 carter_p)) (+ y_s (nth 7 carter_p)) 0))
		    "_non" (setq pt1c (polar ptc pi (nth 2 carter)))
		    "_non" (setq pt2c (polar pt1c (/ pi 2) (* scver (nth 5 carter))))
		    "_non" (setq pt3c (polar pt2c 0 (nth 2 carter)))
		    "_c"
	  )
    
    (command "_pline" "_non" pt2c
		    "_non" pt3c
		    "_non" (polar pt3c (/ pi 2) (* scver 19.3))
		    "_non" (polar pt2c (/ pi 2) (* scver 19.3))
		    "_c"
	  )
    (command "_circle" "_non" (list (+ (/ (nth 2 carter) 2) (car pt2c) -0) (+ (cadr pt2c) 9.7)) 2.5)
    (command "_circle" "_non" (list (- (+ (/ (nth 2 carter) 2) (car pt2c)) (- (/ (nth 2 carter) 2) 15 )) (+ (cadr pt2c) 9.7)) 2.5)
    (command "_circle" "_non" (list (+ (+ (/ (nth 2 carter) 2) (car pt2c)) (- (/ (nth 2 carter) 2) 15 )) (+ (cadr pt2c) 9.7)) 2.5)

    (if (> (/ (nth 2 carter) 2) 450)
      (progn
	(command "_circle" "_non" (list (- (+ (/ (nth 2 carter) 2) (car pt2c)) 300) (+ (cadr pt2c) 9.7)) 2.5)
	(command "_circle" "_non" (list (+ (+ (/ (nth 2 carter) 2) (car pt2c)) 300) (+ (cadr pt2c) 9.7)) 2.5)
	)
      )
    (if (> (/ (nth 2 carter) 2) 750)
      (progn
	(command "_circle" "_non" (list (- (+ (/ (nth 2 carter) 2) (car pt2c)) 600) (+ (cadr pt2c) 9.7)) 2.5)
	(command "_circle" "_non" (list (+ (+ (/ (nth 2 carter) 2) (car pt2c)) 600) (+ (cadr pt2c) 9.7)) 2.5)
	)
      )
    (if (> (/ (nth 2 carter) 2) 1050)
      (progn
	(command "_circle" "_non" (list (- (+ (/ (nth 2 carter) 2) (car pt2c)) 900) (+ (cadr pt2c) 9.7)) 2.5)
	(command "_circle" "_non" (list (+ (+ (/ (nth 2 carter) 2) (car pt2c)) 900) (+ (cadr pt2c) 9.7)) 2.5)
	)
      )
    (if (> (/ (nth 2 carter) 2) 1350)
      (progn
	(command "_circle" "_non" (list (- (+ (/ (nth 2 carter) 2) (car pt2c)) 1200) (+ (cadr pt2c) 9.7)) 2.5)
	(command "_circle" "_non" (list (+ (+ (/ (nth 2 carter) 2) (car pt2c)) 1200) (+ (cadr pt2c) 9.7)) 2.5)
	)
      )    
    )
  )
      (torna_l)
      )
    )

  (if (NOT (OR (= modo "l") (= modo "D")))
    (if (null distpaS) (setq distpaS (carica_f "dibpaS" modalita)))
    (progn
      (setq distpaS_ (read (strcat "(" (leggi entpan "dibpaS") ")")))
      (setq distpas nil)
      (foreach n distpas_
        (setq distpas (cons (list (nth 0 n) (nth 1 n) (nth 5 n) (nth 6 n) (nth 7 n) (nth 8 n) (nth 9 n)) distpas))
      )
    )
    )
  (if (null tabrin) (setq tabrin (carica "rinforzi" "")))
  (if (NOT (OR (= modo "l") (= modo "D")))
     (if (null tabrinf) (setq tabrinf (carica "tabrinf" modalita)))
     (if (leggi entpan "tabrinf") (setq tabrinf (read (strcat "(" (leggi entpan "tabrinf") ")"))))
  )

  (setq listarin nil) (foreach n rinforzi (setq listarin (cons (car n) listarin)))

  (if (null profili) (setq profili (carica "profili" modalita)))
  (if (null mater) (setq mater (carica "mater" modalita)))
  (if (null svilpan) (setq svilpan (carica "svilpan" "")))
  (setq profdadis nil)
  (foreach n svilpan
    (if (/= (nth 17 n) "")
      (setq profdadis (cons (nth 17 n) profdadis))
      )
    )
  (foreach n distpan
      (if  (and (= nompan (car n)) (= "000000000" (cadr n)))
	(progn
	  (command "_layer" "_n" "pan_fori" "")
	  (if (= 0 (nth 6 n))
	    (progn
	      (if (> (nth 2 pan) (nth 8 n))
		(setq pf1 (list (- (- (CAR PT) (nth 8 n)) 0)  (- (* scver (nth 9 n)) (- 0 y_s) (/ (* scver (nth 6 n)) 2.0)) 0) pfq pt)
		(setq pf1 (list (- (- (CAR Pa) (- (nth 8 n) (nth 2 pan))) 0)  (- (* scver (nth 9 n)) (- 0 y_s) (/ (* scver (nth 6 n)) 2.0)) 0) pfq pa)
		)
	      (command "_circle" "_non" pf1 "_d" (nth 5 n))
	      (command "_CHPROP" (ENTLAST) "" "_P" "_LA" "pan_fori" "")
	      (setq lpqscatole (cons pf1 lpqscatole))
	      (command "_zoom" "_c" pf1 300)  ;risoluzione bag autocad 2k quote diamtri
	      (if (/= (nth 5 n) 19.0)
		(command "_dimdiameter" (list (entlast) pf1) "_non" (polar pf1 (* 7 (/ pi 4)) (nth 5 n)))
		)
	      (command "_layer" "_n" "QUOTE-TUBI" "")
	      (command "_CHPROP" (ENTLAST) "" "_P" "_LA" "QUOTE-TUBI" "")
	      (command "_zoom" "_p") ;risoluzione bag autocad 2k quote diamtri
	      (setq pf2 pf1 pf3 pf1 pf4 pf1)
	      )
	    (progn
	      (if (> (nth 2 pan) (nth 8 n))
		(setq pf1 (list (- (- (CAR PT) (nth 8 n)) (/ (nth 5 n) 2.0))  (- (* scver (nth 9 n)) (- 0 y_s) (/ (* scver (nth 6 n)) 2.0)) 0) pfq pt)
		(setq pf1 (list (- (- (CAR Pa) (- (nth 8 n) (nth 2 pan))) (/ (nth 5 n) 2.0))  (- (* scver (nth 9 n)) (- 0 y_s) (/ (* scver (nth 6 n)) 2.0)) 0) pfq pa)
		)
	      (command "_pline" "_non" pf1
		       "_non" (setq pf2 (polar pf1 0 (nth 5 n)))
		       "_non" (setq pf3 (polar pf2 (/ pi 2) (* scver (nth 6 n))))
		       "_non" (setq pf4 (polar pf3 pi (nth 5 n)))
		       "_c")
	      (setq lpqscatole (cons (List (/ (+ (car pf1) (car pf2)) 2) (/ (+ (cadr pf1) (cadr pf3)) 2)) lpqscatole))
	      (command "_CHPROP" (ENTLAST) "" "_P" "_LA" "pan_fori" "")
	      )
	    )
	  )
	)
    )
  (setq pbasef pp)
  (setq pbasef (list (car pbasef) y_s 0))
  (setq pbf pt)
  (setq lispos nil)
  (setq nkit_p nompas)
  (setq lsptqri nil)
  (SETQ D220 NIL)4
  (if (or (= "S" (substr (nth 11 pan) 1 1)) (= "M" (substr (nth 11 pan) 1 1)))
    (progn
      (foreach tkit distpas
	(IF (and (= nkit_p (car tkit)) (= (cadr tkit) "DEM220")) (SETQ D220 (CONS TKIT D220)))
	(if (and (= nkit_p (car tkit)) (member (cadr tkit) listarin))
	  (progn
	    (setq xrin (nth 3 tkit))
	    (setq yrin (nth 4 tkit))
	    (setq dxrin (nth 5 tkit))
	    (setq dyrin (nth 6 tkit))
	    (command "_pline" (list (- (car pt) xrin (/ dxrin 2)) (+ (cadr pt) yrin (- 0 (/ dyrin 2))))
		    (setq prq1 (list (+ (- (car pt) xrin )(/ dxrin 2)) (+ (cadr pt) yrin (- 0 (/ dyrin 2)))))
		    
		    
		    (setq prq2 (list (+ (- (car pt) xrin) (/ dxrin 2)) (+ (cadr pt) yrin (+ 0 (/ dyrin 2)))))
		    (list (- (car pt) xrin (/ dxrin 2)) (+ (cadr pt) yrin (+ 0 (/ dyrin 2)))) "_c")
	    (setq psca (list (+ (- (car pt) xrin) 0) (+ (cadr pt) yrin 0)))
;;;	    (COMMAND "_TEXT" "_S" "SCATOLE" "_m" "_NON" psca "25" "90" (NTH 1 TKIT))
	    (COMMAND "_TEXT" "_S" "SCATOLE" "_m" "_NON" psca "90" (NTH 1 TKIT))
	    (setq lsptqri (cons (list prq1 prq2) lsptqri))
	    (alert "rinforzo puntu")
	    )
	  )
	(if (= nkit_p (car tkit))
	  (progn
	(if (and (= nkit_p (car tkit)) (MEMBER (NTH 1 TKIT) scatoleinkit))
	  (progn
	    (setq psca (list (- (car pbf) (nth 6 tkit)) (+ (cadr pbf) (* SCVER (nth 7 tkit))) 0))
	    (if (/= (strcase (NTH 1 TKIT)) "NO SCATOLA")
;;;	      (COMMAND "_TEXT" "_S" "SCATOLE" "_TR" "_NON" (LIST (+ (CAR PSCA) (/ (nth 8 tkit) 2)) (- (CADR PSCA) 5 (* SCVER (/ (nth 9 tkit) 2))) 0) "25" "0" (NTH 1 TKIT)))
	      (COMMAND "_TEXT" "_S" "SCATOLE" "_TR" "_NON" (LIST (+ (CAR PSCA) (/ (nth 8 tkit) 2)) (- (CADR PSCA) 5 (* SCVER (/ (nth 9 tkit) 2))) 0) "0" (NTH 1 TKIT)))
	    (if (and (/= "NO SCATOLA" (STRCASE (nth 1 tkit))) (assoc (nth 1 tkit) npres))
	      (progn
		(setq pas< (list (- (car psca) (/ (nth 1 (assoc (nth 1 tkit) npres)) 2.0)) (+ (cadr psca) (/ (nth 2 (assoc (nth 1 tkit) npres)) 2.0))))
                (setq pad< (list (+ (car psca) (/ (nth 1 (assoc (nth 1 tkit) npres)) 2.0)) (+ (cadr psca) (/ (nth 2 (assoc (nth 1 tkit) npres)) 2.0))))
		(setq pbd< (list (+ (car psca) (/ (nth 1 (assoc (nth 1 tkit) npres)) 2.0)) (- (cadr psca) (/ (nth 2 (assoc (nth 1 tkit) npres)) 2.0))))
		(setq pbs< (list (- (car psca) (/ (nth 1 (assoc (nth 1 tkit) npres)) 2.0)) (- (cadr psca) (/ (nth 2 (assoc (nth 1 tkit) npres)) 2.0))))
		(command "_pline" "_non" pas< "_non" pad<  "_non" pbd< "_non" pbs< "_C")
		(command "_layer" "_n" "pan_scatole" "")
		(command "_CHPROP" (ENTLAST) "" "_P" "_LA" "pan_scatole" "")
	    )
	      )
	    )
	  )
		(if (and (= nkit_p (car tkit)) (or (= "DM-00002" (nth 1 tkit)) (= "DM-00001" (nth 1 tkit))))

;;;	(if (and (= nkit_p (car tkit)) (or (= "DEM239" (nth 1 tkit)) (= "DEM217" (nth 1 tkit))))
	  (progn
	(vai_l "pan_boccole")
	(setq elet "Si")
	    (command "_INSERT" (strcat (cadr (assoc 'perc_programma parametri)) "NuoviFori\\" (nth 1 tkit) "-" (RTOS (NTH 5 TKIT) 2 0)) "_NON"
		    (SETQ PPROVA (LIST (- (car pt) (nth 6 tkit)) (+ (cadr pt) (nth 7 tkit)))) "1" "1" "0")
	(torna_l)
	    )lre 
	  )
	(setq feltro (cadr (assoc 'feltro parametri)))
	(if (and (= nkit_p (car tkit)) (= feltro (nth 1 tkit)))
	  (progn
	    (IF PANANG  (SETQ FPT_1 PA1) (SETQ FPT_1 PT1))
	(vai_l "pan_feltro")
	    (setq pft1 (LIST (- (- (car pt) (nth 6 tkit)) (/ (nth 8 tkit) 2)) (+ (+ (cadr pt) (nth 7 tkit)) (/ (nth 9 tkit) 2))))
	(if (> (car FPT_1) (car pft1))
	    (setq pft1 (list (+ (car FPT_1) 5) (cadr pft1))))
	    (setq pft2 (LIST (+ (- (car pt) (nth 6 tkit)) (/ (nth 8 tkit) 2)) (+ (+ (cadr pt) (nth 7 tkit)) (/ (nth 9 tkit) 2))))
	(if (< (car pt) (car pft2))
	    (setq pft2 (list (- (car pt) 5) (cadr pft2))))
	    (setq pft3 (LIST (+ (- (car pt) (nth 6 tkit)) (/ (nth 8 tkit) 2)) (- (+ (cadr pt) (nth 7 tkit)) (/ (nth 9 tkit) 2))))
	(if (< (car pt) (car pft3))
	    (setq pft3 (list (- (car pt) 5) (cadr pft3))))
	    (setq pft4 (LIST (- (- (car pt) (nth 6 tkit)) (/ (nth 8 tkit) 2)) (- (+ (cadr pt) (nth 7 tkit)) (/ (nth 9 tkit) 2))))
	(if (> (car FPT_1) (car pft4))
	    (setq pft4 (list (+ (car FPT_1) 5) (cadr pft4))))
	
	    (command "_pline"
		     "_non" pft1
		     "_non" pft2
		     "_non" pft3
		     "_non" pft4
		     "_C")
	    (command "_hatch" "_P" "cross" 3 0 "_S" (entlast) "" )
	    (torna_l)
	    )lre
	  )
	(if (and (= nkit_p (car tkit)) (setq nomef (findfile (strcat (cadr (assoc 'perc_programma parametri)) "NuoviFori\\" (nth 1 tkit) ".dwg"))))
	  (progn
	    (vai_l "pan_boccole")
	    (if (and (= -2 (nth 8 tkit)) (setq nomefx (findfile (strcat (cadr (assoc 'perc_programma parametri)) "NuoviFori\\" (nth 1 tkit) "$.dwg"))))
	      (command "_insert" nomefx "_non" (list (- (car pt) (nth 6 tkit)) (+ (cadr pt) (nth 7 tkit))) (abs 1) (abs 1)  (nth 9 tkit))
	      (command "_insert" nomef "_non" (list (- (car pt) (nth 6 tkit)) (+ (cadr pt) (nth 7 tkit))) (nth 8 tkit) (abs (nth 8 tkit))  (nth 9 tkit))
	      )
	    (torna_l)
	    )lre 
	  )
	(if (and (= nkit_p (car tkit)) (setq nomef (findfile (strcat (cadr (assoc 'perc_programma parametri)) "NuoviFori\\" (nth 1 tkit) ".txt"))))
	  (progn
	    (vai_l "pan_tubi")
	    (setq elet "Si")
	    (command "_COLOR" "bylayer")
	    (command "_ucs" "_o" "_non" pt)
	    (command "_line" "_non" (setq ptubo1 (list (- 0.0 (nth 6 tkit)) (+ 0.0 (nth 7 tkit)))) "_non" (polar ptubo1 (/ pi 2) (nth 5 tkit)) "")
	    (command "_ucs" "_w")	
	    (allega (entlast) "ntubo" (nth 1 tkit))
	    (torna_l)
	    )
	  )
	)
	  )
	(if (and (= nkit_p (car tkit)) (setq ppdd (assoc (cadr tkit) profili)) (member (nth 2 ppdd) profdadis))
	  (progn
	    (setq ppdd_p (list (- (car pt) (nth 6 tkit)) (+ (cadr pt) (nth 7 tkit))))
	    (vai_l "pan_Profili")
	    (command "_pline" "_non" (list (- (car ppdd_p) (/ (nth 5 ppdd) 2)) (- (cadr ppdd_p) (/ (nth 4 ppdd) 2)))
		     "_non" (list (+ (car ppdd_p) (/ (nth 5 ppdd) 2)) (- (cadr ppdd_p) (/ (nth 4 ppdd) 2)))
		     "_non" (list (+ (car ppdd_p) (/ (nth 5 ppdd) 2)) (+ (cadr ppdd_p) (/ (nth 4 ppdd) 2)))
		     "_non" (list (- (car ppdd_p) (/ (nth 5 ppdd) 2)) (+ (cadr ppdd_p) (/ (nth 4 ppdd) 2)))
		     "_c")
	    (torna_l)
	    )
	  )
	(if (= nkit_p (car tkit)) 
	  (progn
	    (setq ppdd (cadr tkit))
	    (if (and (assoc ppdd profili) (= "DEM297" (nth 2 (assoc ppdd profili))))
	      (progn
		(setq ppdd1 (list (- (car pt) (- (nth 6 tkit) (/ (nth 5 (assoc ppdd profili)) 2))) (+ y_s (- (nth 7 tkit) (/ (nth 4 (assoc ppdd profili)) 2)))))
		(setq ppdd2 (list (- (car pt) (- (nth 6 tkit) (/ (nth 5 (assoc ppdd profili)) 2))) (+ y_s (+ (nth 7 tkit) (/ (nth 4 (assoc ppdd profili)) 2)))))
		(setq ppdd3 (list (- (car pt) (+ (nth 6 tkit) (/ (nth 5 (assoc ppdd profili)) 2))) (+ y_s (+ (nth 7 tkit) (/ (nth 4 (assoc ppdd profili)) 2)))))
		(setq ppdd4 (list (- (car pt) (+ (nth 6 tkit) (/ (nth 5 (assoc ppdd profili)) 2))) (+ y_s (- (nth 7 tkit) (/ (nth 4 (assoc ppdd profili)) 2)))))
		(vai_l "pan_Profili")
		(command "_pline" "_non" ppdd1 "_non" ppdd2 "_non" ppdd3 "_non" ppdd4 "_c")
		(torna_l)
		)
	      )
	    )
	  )




	
	(if (null dibldr) (setq dibldr (carica "dibldr" modalita)))
(if (and (= nkit_p (car tkit)) (setq ppdd (assoc (cadr tkit) mater)))
	      (progn
		(setq splana (nth 5 ppdd))
;      (alert "mater")
      (setq ppdd_l (setq ppdd_p (list (- (car pt) (nth 6 tkit)) (+ (cadr pt) (nth 7 tkit)))))
      	(vai_l "pan_Lana")

      (command "_pline" "_non" (setq plf ppdd_p)
	      "_non" (list (- (car ppdd_p) (/ (nth 3 ppdd) 1)) (- (cadr ppdd_p) 0))
	      "_non" (list (- (car ppdd_p) (/ (nth 3 ppdd) 1)) (+ (cadr ppdd_p) (/ (nth 4 ppdd) 1)))
              "_non" (list (car ppdd_p)  (+ (cadr ppdd_p) (/ (nth 4 ppdd) 1)))
	      "_c")
        (foreach ln dibldr
	  (if (and (= (car ppdd) (car ln))(= "000000000" (nth 1 ln)))
	    (progn
	      (setq plfxx (list (- (car plf) (nth 4 ln)) (+ (cadr plf) (nth 5 ln))))
	      (if (= 0 (nth 3 ln))
	(command "_circle" plfxx (/ (nth 2 ln)2.0))
	      (command "_pline" "_non" (list (- (car plfxx) (/ (nth 2 ln) 2.0)) (- (cadr plfxx) (/ (nth 3 ln) 2.0)))
		      "_non" (list (- (car plfxx) (/ (nth 2 ln) 2.0)) (+ (cadr plfxx) (/ (nth 3 ln) 2.0)))
		      "_non" (list (+ (car plfxx) (/ (nth 2 ln) 2.0)) (+ (cadr plfxx) (/ (nth 3 ln) 2.0)))
		      "_non" (list (+ (car plfxx) (/ (nth 2 ln) 2.0)) (- (cadr plfxx) (/ (nth 3 ln) 2.0)))
		      "_c")
		)
	      )
	    )
	  )
      	(torna_l)

      )
      )
	)
      
      
      
      
  (setq xpq 0)
  (if lsptqri
    (progn
;;;      (setq cart_rinf "R")
      (command "_dim1" "_res" "rinforzi")
      (foreach n lsptqri 
	
	(if (= (rtos (car (car n))) (rtos xpq))
	    (if (/= modo "k") (command "_dimlinear" "_non" pt "_non" (car n)  "_v" "_non" (list (+ 120 (car (car n))) (cadr (car n)))))
	    (if (/= modo "k") (command "_dimlinear" "_non" pt "_non" (car n)  "_v" "_non" (list (+ 60 (car (car n))) (cadr (car n)))))
	  )
	(foreach p (cdr n)
	  (if (/= modo "k") (command "dimcontinue" "_non" p "" ""))
	)
	(setq xpq (car (car n)))
	)
	(command "_dim1" "_res" "pannelli")
      )
    )
   
  )
    
      )
  (VAI_L "pan_dem220")
  (if (and ENTLAST220 (null d220)) (command "_erase" ENTLAST220 ""))
  (FOREACH D D220
    (COMMAND "_INSERT" "DEM220" "_NON" (LIST (CAR P220) (+ (CADR P220) (NTH 7 D))) "1" "1" "0")
    )
  (torna_l)
  (setq lisptqr nil)
  (setq lisptqr (cons (cadr pt) lisptqr))
  (setq cerfbl nil)
  (setq lisdot nil)
;;;  (if (NOT (OR (= modo "l") (= modo "D")))
;;;      (if (null lanacer) (setq lanacer (carica "lanacer" modalita)))
;;;      (if (leggi entpan "lanacer") (setq lanacer (read (strcat "(" (leggi entpan "lanacer") ")"))))
;;;    )
  (setq lista_rt nil)
  (setq nomerinft nil)
  (foreach n distpaS
      (if (and (= nompas (car n)) (assoc (nth 1 n) lanacer))
	       (setq lisdot (cons (nth 3 n) lisdot))
      )
    
      (if (and (= nompas (car n))(assoc (cadr n) tabrinf))
	(progn
          (setq cerfbl (nth 2 (assoc (nth 1 n) tabrinf)))
          (setq hrin (nth 1 (assoc (nth 2 (assoc (NTH 1 n) tabrinf)) tabrin)))
	  (IF (= HRIN 0) (SETQ HRIN  (nth 4 (assoc (nth 1 n) tabrinf))))
	      (setq pr1 (list (- (car pt)(nth 6 n)) (+ (cadr pt) (- (* scver (nth 7 n)) (* scver (/ hrin 2)))) 0))
;;;	  (if (= "N" (substr (nth 11 pan) 1 1)) (vai_l "pan_rinforzi")
	    (vai_l "rinforzi")
;;;	    )
	  (if (/= "N" (substr (nth 11 pan) 1 1))
	    (progn
	      (if (= "VER" (nth 5 (assoc (NTH 1 n) tabrinf)))
		(progn
		  (setq cart_rinf "R")
		  (setq pr1 (list (+ (- (car pt)(nth 6 n)) (/ hrin 2)) (+ (cadr pt) (* scver (nth 7 n))) 0))
		  (command "_pline" "_non" pr1
		  "_non" (setq pr2 (polar pr1 (/ pi 2) (nth 3 (assoc (nth 1 n) tabrinf))))
		  "_non" (setq pr3 (polar pr2 (/ pi 1) (* scver hrin)))
		  "_non" (setq pr4 (polar pr3 (* 3 (/ pi 2)) (nth 3 (assoc (nth 1 n) tabrinf))))
		  "_c"
	  )
		  (setq pr1a pr1  pr2a pr2  pr3a pr3  pr3a pr4 )
		  (SETQ TESTO_RINF (NTH 2 (ASSOC (NTH 1 N) TABRINF)))
		  
;;;		  	       (command "_text" "_C" "_non" (list (/ (+ (car pr1) (car pr4)) 2) (/ (+ (cadr pr3) (cadr pr1)) 2)) "20" "90" TESTO_RINF)
		  	       (command "_text" "_S" "SCATOLE" "_C" "_non" (list (/ (+ (car pr1) (car pr4)) 2) (/ (+ (cadr pr3) (cadr pr1)) 2)) "90" TESTO_RINF)
               (command "_dim1" "_res" "RINFORZI")
	       (if (/= modo "k") (progn
				   (SETQ LISPTRV (CONS PR1 LISPTRV))
				   (SETQ LISPTRV (CONS PR4 LISPTRV))
;;;				   (command "_dimlinear" "_non" pr1 "_non" pr4 "_h" "_NON" (list (- (car pR1) (/ (nth 3 (assoc (nth 1 n) tabrinf)) 2)) (+ (cadr pR1) (* scver (/ hrin 2)) -90)))
;;;				   (command "_dimlinear" "_non" pt "_non" pr4 "_h" "_NON" (list (- (car pR1) (/ (nth 3 (assoc (nth 1 n) tabrinf)) 2)) (+ (cadr pR1) (* scver (/ hrin 2)) -90)))
;;;				   (command "_dimlinear" "_non" pt1 "_non" pr1 "_h" "_NON" (list (- (car pR1) (/ (nth 3 (assoc (nth 1 n) tabrinf)) 2)) (+ (cadr pR1) (* scver (/ hrin 2)) -90)))
				   ))
               (setvar "dimlfac" (/ 1 scver))

		  )
		(progn
		  (setq cart_rinf "R")
		  (setq pr1 (list (- (car pt)(nth 6 n)) (+ (cadr pt) (- (* scver (nth 7 n)) (* scver (/ hrin 2)))) 0))
	      (command "_pline" "_non" pr1
		  "_non" (setq pr2 (polar pr1 pi (nth 3 (assoc (nth 1 n) tabrinf))))
		  "_non" (setq pr3 (polar pr2 (/ pi 2) (* scver hrin)))
		  "_non" (setq pr4 (polar pr3 (* 2 pi) (nth 3 (assoc (nth 1 n) tabrinf))))
		  "_c"
	  )(setq pr1a pr1  pr2a pr2  pr3a pr3  pr3a pr4 )
		  (SETQ TESTO_RINF (NTH 2 (ASSOC (NTH 1 N) TABRINF)))
;;;		  	       (command "_text" "_C" "_non" (list (- (car pR1) (/ (nth 3 (assoc (nth 1 n) tabrinf)) 2)) (+ (cadr pR1) (* scver (/ hrin 2)) 5)) "20" "0" TESTO_RINF)
		  	       (command "_text" "_S" "SCATOLE" "_C" "_non" (list (- (car pR1) (/ (nth 3 (assoc (nth 1 n) tabrinf)) 2)) (+ (cadr pR1) (* scver (/ hrin 2)) 5)) "0" TESTO_RINF)
               (command "_dim1" "_res" "RINFORZI")
	       (if (/= modo "k") (command "_dimlinear" "_non" pr1a "_non" pR2a "_h" "_NON" (list (- (car pR1) (/ (nth 3 (assoc (nth 1 n) tabrinf)) 2)) (+ (cadr pR1) (* scver (/ hrin 2)) -50))))
               (setvar "dimlfac" (/ 1 scver))
))
	      
	      )
;;;	    (progn
;;;	  (setq hrin2 (nth 2 (assoc (nth 2 (assoc (NTH 1 n) tabrinf)) tabrin)))
;;;	  (setq pr1a (polar pr1 (/ pi 2) (/ (- (* scver hrin) (* scver hrin2)) 2)))
;;;	  (command "_pline" "_non" pr1a
;;;		  "_non" (setq pr2a (polar pr1a pi (nth 3 (assoc (nth 1 n) tabrinf))))
;;;		  "_non" (setq pr3a (polar pr2a (/ pi 2) (* scver hrin2)))
;;;		  "_non" (setq pr4a (polar pr3a 0 (nth 3 (assoc (nth 1 n) tabrinf))))
;;;		  "_c"
;;;	  )
;;;	  (allega (entlast) "codrin" (nth 0 (assoc (nth 2 (assoc (NTH 1 n) tabrinf)) tabrin)))
;;;	  )
	    )
	  (torna_l)
	  (setq hrin_q (nth 1 (assoc (nth 2 (assoc (NTH 1 n) tabrinf)) tabrin)))
	  
	      
		  
	   (setq lisptqr (cons (cadr pr2a) lisptqr))
	   (setq lisptqr (cons (cadr pr3a) lisptqr))
	)
      )
    )
    (IF LISPTRV
      (PROGN
	(command "_dim1" "_res" "RINFORZI")
	(IF PANANG (SETQ LISPTRV (CONS PA1 LISPTRV)) (SETQ LISPTRV (CONS PT1 LISPTRV)))
        (SETQ LISPTRV (CONS PT LISPTRV))
	(setq LISPTRV (vl-sort LISPTRV (function (lambda (e1 e2) (< (CAR e1) (CAR e2))))))
	(SETQ PZ1 (CAR LISPTRV))
	(FOREACH PZ2 (CDR LISPTRV)
	  (command "_dimlinear" "_non" PZ1 "_non" PZ2 "_h" "_NON" (POLAR PZ1 (* 3 (/ PI 2)) 100))
	  (SETQ PZ1 PZ2)
	  )
	)
      )
    (setq lisptqr (cons (cadr pt3) lisptqr))
    (setq lisptqr (vl-sort lisptqr (function (lambda (e1 e2) (< e1 e2)))))
    (setvar "dimlfac" (/ 1 scver))
    (IF (< 2 (LENGTH LISPTQR))
      (PROGN
        (if (/= modo "k") (command "_dimlinear" "_non" (list (car pt1) (nth 0 lisptqr)) "_non" (list (car pt1) (nth 1 lisptqr)) "_V" "_NON"))
	(IF PANANG
	  (if (/= modo "k") (COMMAND (polar (list (car pA1) (nth 0 lisptqr)) pi 70)))
	  (if (/= modo "k") (COMMAND (polar (list (car pt1) (nth 0 lisptqr)) pi 70)))
	)
	(SETQ OLDN (nth 1 lisptqr))
        (if (/= modo "k") (command "_dimcontinue"))
	
        (forEAch n (cddr lisptqr)
          (IF (/= (RTOS N) (RTOS OLDN)) (if (/= modo "k") (command "_non" (list (car pt1) n))))
	  (SETQ OLDN N)
        )
        (if (/= modo "k") (command "" ""))
      )
    )
  (setq lista_rt (vl-sort lista_rt (function (lambda (e1 e2) (< (cadr e1) (cadr e2))))))
  (if (and lista_rt (/= modo "k")) (command "_dimlinear" "_non" (nth 1 lista_rt) "_non" (polar (nth 1 lista_rt) 0 lunghrt) "_h" "_NON" (polar (nth 1 lista_rt) (/ pi 2) 20)))
  (vai_l "isolamento")
  (command "_layer" "_of" "rinfor*" "")
  (foreach n lisdot
    (command "_-bHATCH" "_p" "DOTS" "10" "45" (polar (polar pbf pi (+ n 30)) (/ pi 2) 100) ""))
  (torna_l)  
  (command "_layer" "_on" "rinfor*" "")

     (IF (= modo "n") (distbase_pa "no" nompas (list 1000 0 0) 0.3))
    (if (/= modo "k") (if cerfbl (if (findfile cerfbl) (command "_insert" cerfbl "_non" pt "1" "1" "0"))))
    (command "_linetype" "_set" "ISOLAMENTO" "")
    (VAI_L "ISOLAMENTO")
    (SETVAR "LTSCALE" 0.06)
    (if panDRI
      (PROGN
        (command "_PLINE" "_NON" p1_r "_NON" p2_r "")
	(command "_OFFSET" "10" (LIST (SETQ ENTD (ENTLAST)) p2_r) "_non" (polar p2_r (+ (angle p1_r p2_r) (/ pi 2)) 10) "")
	(ENTDEL ENTD)
     )
      (PROGN
        (command "_PLINE" "_NON" p1_r "_NON" p2_r "_NON" p3_r "")
	(command "_OFFSET" "10" (LIST (SETQ ENTD (ENTLAST)) p1_r) "_non" (polar p1_r (+ (angle p1_r p2_r) (/ pi 2)) 10) "")
	(ENTDEL ENTD)
     )
    )
    (command "_linetype" "_set" "BYLAYER" "")
    (TORNA_L)
  (command "_zoom" "_E")
  (setq lpqscatole (cons pt1 lpqscatole))
  (setq lpqscatole (cons pt3 lpqscatole))
  (if pa1 (setq lpqscatole (cons pa1 lpqscatole)))
  (setq lpqscatolev (vl-sort lpqscatole (function (lambda (e1 e2) (> (CAdR e1) (CAdR e2)))))) 
  (setq lpqscatoleh (vl-sort lpqscatole (function (lambda (e1 e2) (> (CAR e1) (CAR e2))))))
  (setq np -1)
  (setq lpqscatolev_ (list  (nth 0  lpqscatolev)))
  (foreach p (cdr lpqscatolev)
    (if (> (distance p (nth (setq np (+ 1 np))  lpqscatolev)) 0) (setq lpqscatolev_ (cons  p lpqscatolev_)))
    )
    (setq np -1)
  (setq lpqscatoleh_ (list  (nth 0  lpqscatoleh)))
  (foreach p (cdr lpqscatolev)
    (if (> (distance p (nth (setq np (+ 1 np))  lpqscatoleh)) 0) (setq lpqscatoleh_ (cons  p lpqscatoleh_)))
    )
  (command "_dim1" "_res" "rinforzi")
  (if (> (length lpqscatolev_) 2)
    (progn
  (command "_dim1" "_ver" "_non" (nth 0 lpqscatolev_) "_non" (nth 1 lpqscatolev_) "_non" (list (+ (car pt3) 100) (cadr pt3)) "")
    (foreach px (cdr (cdr lpqscatolev_))
      (command "_dimcontinue" "_non" px )
      )
    (command "" "")
    )
    )
  (if (> (length lpqscatoleh_) 2)
    (progn
  (command "_dim1" "_hor" "_non" (nth 0 lpqscatoleh_) "_non" (nth 1 lpqscatoleh_) "_non" (list (- (car pt) 0) (- (cadr pt) 200)) "")
    (foreach px (cdr (cdr lpqscatoleh_))
      (command "_dimcontinue" "_non" px )
      )
    (command "" "")
    )
    )
(setq ptperq nil)
(setq ecarter nil)
(retro nil splana (nth 3 (assoc nompas lispas_g)) elet)
  (if (and (= tipomb "Bifacciale") ptperq)
    (progn
      (command "_dim1" "_ali" "_non" (nth 0 ptperq) "_non"
	      (nth 1 ptperq) "_non" (polar (nth 0 ptperq) (+ (angle(nth 0 ptperq)
								   (nth 1 ptperq)) (/ pi 2)) 100) "")
      (setq entg (entget (entlast)))
      (setq entm (subst (cons 1 "RT <>") (assoc '1 entg) entg))
      (entmod entm)
      (if (nth 2 ptperq)
	(progn
	  (command "_dim1" "_ali" "_non" (nth 1 ptperq) "_non"
	      (nth 2 ptperq) "_non" (polar (nth 1 ptperq) (+ (angle(nth 1 ptperq)
								   (nth 2 ptperq)) (/ pi 2)) 100) "")
          (setq entg (entget (entlast)))
      (setq entm (subst (cons 1 "RT <>") (assoc '1 entg) entg))
      (entmod entm)
	  )
	)

      )
    )
  (if ecarter
    (progn
      (setvar "pickstyle" 0)
      (setq discp (+ (distance p1 p2) 300))
      (command "_copy" (nth 1 ecarter) "" "_NON" "0,0,0" "_non" (list (- 0 discp) 0 0))
      (setvar "pickstyle" 1)
      (setq pqc1 (list (- (car (nth 2 ecarter)) discp)  (cadr (nth 2 ecarter)) 0))
      (setq pqc2 (list (- (car (nth 3 ecarter)) discp)  (cadr (nth 3 ecarter)) 0))
      
                 (command "_dim1" "_ali" "_non" pqc1
			 "_non" pqc2
			 "_non" (polar pqc1 (+ (angle pqc1 pqc2) (/ pi 2)) 100) "")
      (cond ((= "CAS" (nth 0 ecarter))
	                      (command "_dim1" "_ali" "_non" pqc2
			 "_non" (polar pqc2 (angle pqc2 pqc1) (nth 4 ecarter))
			 "_non" (polar pqc1 (- (angle pqc1 pqc2) (/ pi 2)) 100) "")
	     )
	    ((= "CAD" (nth 0 ecarter))
	                      (command "_dim1" "_ali" "_non" pqc2
			 "_non" (polar pqc2 (angle pqc2 pqc1) (nth 4 ecarter))
			 "_non" (polar pqc1 (- (angle pqc1 pqc2) (/ pi 2)) 100) "")
	     )
	    ((= "CVD" (nth 0 ecarter))
	                      (command "_dim1" "_ali" "_non" pqc2
			 "_non" (polar pqc2 (- (angle pqc2 pqc1) (/ pi 2)) (nth 4 ecarter))
			 "_non" (polar pqc2 (- (angle pqc2 pqc1) pi) 100) "")
	     )
	    ((= "CVS" (nth 0 ecarter))
	                      (command "_dim1" "_ali" "_non" pqc2
			 "_non" (polar pqc2 (+ (angle pqc2 pqc1) (/ pi 2)) (nth 4 ecarter))
			 "_non" (polar pqc2 (- (angle pqc2 pqc1) pi) 100) "")
	     )
	    )


      )
    )
  
  (setvar"mirrtext" 0)
    (command "_mirror" "_C" (list (+ (car pp) 1000) (+ (cadr pp) 450)) (list (- (car pp) 2000) (+ (cadr pp) 2500 450)) "" "_non" pm_r "_non" (polar pm_r (/ pi 2) 1000) "_n")
  (command "_move" "_p" "" "_non" pm_R "_non" (polar pm_R 0 2250))
;;;  (command "_mirror" "_c" (list (+ (car pp) 1000) (+ (cadr pp) 450)) (list (- (car pp) 2000) (- (cadr pp) 2500 )) "" (list (+ (car pp) 0) (+ (cadr pp) 0)) (list (- (car pp) 1000) (+ (cadr pp) 0)) "_y")
  (IF (= modo "n")
    (PROGN
    (setq gri (ssget "x" (list '(0 . "INSERT") '(2 . "cartiglio"))))
    (setq intes (ssname gri 0))
    (setq ent (entnext intes))
    (setq entg (entget ent))
    (setq entn (subst (cons 1 nompas) (assoc '1 entg) entg))
    (entmod entn)
    (setq data (strcat (substr (rtos (getvar"cdate") 2 0) 7 2) "." (substr (rtos (getvar"cdate") 2 0) 5 2) "." (substr (rtos (getvar"cdate") 2 0) 3 2)))
     
    (setq ent (entnext ent))
    (setq entg (entget ent))
    (setq entn (subst (cons 1 data) (assoc '1 entg) entg))
    (entmod entn)
    
    (setq ent (entnext ent))
    (setq entg (entget ent))
    (setq entn (subst (cons 1 (strcat nompas )) (assoc '1 entg) entg))
    (entmod entn)

    (setq ent (entnext ent))
    (setq entg (entget ent))
;;;    (SETQ TITOLO (STRCAT "ASSIEME PANNELLO " TIPOPAN "  " cart_for cart_ang cart_rinf))
    (setq titolo (nth 2 (assoc nompas lispas_g)))
    (setq entn (subst (cons 1 titolo) (assoc '1 entg) entg))
    (entmod entn)
    (ENTUPD INTES)
    )
    )
  (if (= modo "D") ;miooo
    (progn
              (if panang
    
    (progn (setq supp1 pt3)
           (setq supp2 pt2)
      (setq supp3 pa2)
      )
    (progn (setq supp1 pt3)
           (setq supp2 pt2)
      )
    )
  (piegapannello entpan)

      (setq grhh (ssadd))
      (setq ent entblocco)
      (while (setq ent (entnext ent))
	(setq grhh_C (ssadd))
	(setq grhh_c (ssadd ent grhh_C))
	(if grhh_c (setq grhh (ssadd ent grhh)))
      )
      (setq pp_rif (list (car pp_rif) (+ (cadr pp_rif) 200)))

      (command "_group" "_c" "*" (strcat "Anteprima-" (car pan)) grhh (entlast) "")
    )
    )
    (setvar"pickstyle" 0)
  (if (= modo_old "S")
    (setq pp pp_s pik pik_S ulta ulta_s angk1 angk1_s angk angk_s)
  )
;;;  (setq pp pp_x_k)
  (quote0-90)
    pan
)


(DEFUN VAI_L (NOME)
  (SETQ VAI_LAYER (GETVAR"CLAYER"))
  (command "_LAYER" "_M" NOME "")
)


(DEFUN TORNA_L ()
  (command "_LAYER" "_M" VAI_LAYER "")
)

(defun distbase_pa (testa assieme pt scala)
;;;  (command "_undo" "_g")
  (setq listad nil)
  (setq pos 0)
  (setq rigedist nil)
  (if (null rigedist)
    (progn
  (setq rigedist (carica "anag" ""))

  (if (findfile (strcat modalita "$$pannelli" ".txt"))
    (setq file (open (findfile (strcat modalita "$$pannelli" ".txt")) "r"))
    (setq file (open (findfile (strcat modalita "pannelli" ".txt")) "r"))
    )
  (while (setq r (read-line file))
    (setq r (read (strcat "(" r ")")))
    (setq rigedist (cons (list (nth 0 r) (nth 4 r) (nth 2 r)) rigedist))
  )
  (close file)

  (if (findfile (strcat modalita "$$pannellil" ".txt"))
    (setq file (open (findfile (strcat modalita "$$pannellil" ".txt")) "r"))
    (setq file (open (findfile (strcat modalita "pannellil" ".txt")) "r"))
    )
  (while (setq r (read-line file))
    (setq r (read (strcat "(" r ")")))
    (setq rigedist (cons (list (nth 0 r) (nth 12 r) (nth 1 r)) rigedist))
  )
  (close file)
  (if (findfile (strcat modalita "$$pannellil_r" ".txt"))
    (setq file (open (findfile (strcat modalita "$$pannellil_R" ".txt")) "r"))
    (setq file (open (findfile (strcat modalita "pannellil_R" ".txt")) "r"))
    )
  (while (setq r (read-line file))
    (setq r (read (strcat "(" r ")")))
    (setq rigedist (cons (list (nth 0 r) (nth 12 r) (nth 1 r)) rigedist))
  )
  (close file)

  (setq file (open (findfile (strcat modalita "mater" ".txt")) "r"))
  (while (setq r (read-line file))
    (setq r (read (strcat "(" r ")")))
    (setq rigedist (cons (list (nth 0 r) (nth 10 r) (nth 1 r)) rigedist))
  )
  (close file)

  (setq file (open (findfile (strcat modalitac "tabrinf" ".txt")) "r"))
  (while (setq r (read-line file))
    (setq r (read (strcat "(" r ")")))
    (setq rigedist (cons (list (nth 0 r) (nth 6 r) (nth 1 r)) rigedist))
  )
  (close file)
  (setq file (open (findfile (strcat modalitac "profili" ".txt")) "r"))
  (while (setq r (read-line file))
    (setq r (read (strcat "(" r ")")))
    (setq rigedist (cons (list (nth 0 r) "Nr" (nth 1 r)) rigedist))
  )
  (close file)

  (setq distpas dibpas)
  (if (null distpas) (setq dibpas (setq distpas (carica_f "dibpas" modalita))))
  (foreach n distpas
   (if (and (/= "" (cadr n)) (= assieme (car n)))
    (if (null (assoc (cadr n) rigedist))
      (progn (if (= "$" (substr (cadr n) (strlen (cadr n)) 1))
	       (if (null (assoc (substr (cadr n) 1 (- (strlen (cadr n))1)) rigedist))
		 (alert (strcat "Codice " (cadr n) " non in anarafica !!!"))
		 (setq listad
                   (cons
                     (list (substr (cadr n) 1 (- (strlen (cadr n))1)) (nth 2 (assoc (substr (cadr n) 1 (- (strlen (cadr n))1)) rigedist)) (nth 1 (assoc (substr (cadr n) 1 (- (strlen (cadr n))1)) rigedist)) (rtos (nth 2 n) 2 2))
                     listad
                   )
                  )
		 )
        (IF (/= "NO SCATOLA" (STRCASE (cadr n))) (alert (strcat "Codice " (cadr n) " non in anarafica !!!")))
	)
	)
      (setq listad
         (cons
            (list (cadr n) (nth 2 (assoc (cadr n) rigedist)) (nth 1 (assoc (cadr n) rigedist)) (rtos (nth 5 n) 2 2))
            listad
         )
      )
     )
   )
  )
    )
  )
  (setvar"expert" 5)
  
  (if (= testa "si")
    (progn
      (command "_INSERT" "testatab" "_non" pt scala scala "0" assieme (nth 2 (assoc assieme rigedist)))
      (command "_-group" "_c" (substr assieme 2 2) "" (entlast) "")
    )
    (command "_-group" "_c" (substr assieme 2 2) "" "")
  )
  (setvar"expert" 1)
  (setq listam listad)
  (setq listad nil)
  (foreach n listam
    (if (assoc (car n) listad)
      (setq listad
	     (subst (list (nth 0 n) (nth 1 n) (nth 2 n) (rtos (+ (atof (nth 3 n)) (atof (nth 3 (assoc (car n) listad)))) 2 2))
		    (assoc (car n) listad)
		    listad
	     )
      )
      (setq listad (cons n listad))
    )
  )
  (SETQ DIBPAN (CARICA "DIBPAN" MODALITA))
  (SETQ LISTAK LISTAD LISTAD NIL)
  (FOREACH N LISTAK
    (IF (ASSOC (NTH 0 N) DIBPAN)
      (PROGN
        (SETQ SVI (NTH 1 (ASSOC (NTH 0 N) DIBPAN)))
	(SETQ NN (LIST (NTH 0 N) (STRCAT (NTH 1 N) " - Cod Sviluppo:  " svi) (NTH 2 N) (NTH 3 N)))
	(SETQ LISTAD (CONS Nn LISTAD))
;;;	(ALERT "PIPPO")
	)
      (SETQ LISTAD (CONS N LISTAD)))
    )
  (setq listad (reverse listad))
  (SETQ DIBPAN (CARICA "DIBPAN_r" MODALITA))
  (SETQ Sviluppi_r (CARICA "Sviluppi_r" MODALITA))
  (SETQ LISTAK LISTAD LISTAD NIL)
  (FOREACH N LISTAK
    (IF (ASSOC (NTH 0 N) DIBPAN) 
      (PROGN
        (if (assoc (NTH 1 (ASSOC (NTH 0 N) DIBPAN)) Sviluppi_r) (SETQ SVI (NTH 1 (ASSOC (NTH 0 N) DIBPAN)))
	  (SETQ SVI (NTH 1 (ASSOC (NTH 0 N) (reverse DIBPAN))))
	  )
	(SETQ NN (LIST (NTH 0 N) (STRCAT (NTH 1 N) " - Cod Sviluppo:  " svi) (NTH 2 N) (NTH 3 N)))
	(SETQ LISTAD (CONS Nn LISTAD))
	)
      (SETQ LISTAD (CONS N LISTAD)))
    )
  (setq listad (reverse listad))
  
  (SETQ POS 0)
  (foreach n listad
      (command "_INSERT" "rigatab" "_non" pt scala scala "0")
      (cond ((= "MQ" (strcase (nth 2 n)))
             (command (rtos (setq pos (+ 1 pos)) 2 0) (nth 0 n) (nth 1 n) (nth 2 n) (rtos (/ (atof (nth 3 n)) 1000000)2 2))
	    )
	    ((= "ML" (strcase (nth 2 n)))
             (command (rtos (setq pos (+ 1 pos)) 2 0) (nth 0 n) (nth 1 n) (nth 2 n) (rtos (/ (atof (nth 3 n)) 1000)2 2))
	    )
	    ((= "KG" (strcase (nth 2 n)))
             (command (rtos (setq pos (+ 1 pos)) 2 0) (nth 0 n) (nth 1 n) (nth 2 n) (rtos (/ (atof (nth 3 n)) 1000)2 2))
	    )
	    ("t"
             (command (rtos (setq pos (+ 1 pos)) 2 0) (nth 0 n) (nth 1 n) (nth 2 n) (rtos (/ (atof (nth 3 n)) 1)2 0))
	    )
      )
      (if (= testa "si") (command "_-group" "_add" (substr assieme 2 2) (entlast) ""))
    (setq pt (list (car pt) (- (cadr pt) (* scala 100) 0)))
  )
  (setq $pt$ pt)
)
(DEFUN c:NEW1PAS ()
  (setq modalita (cadr (assoc 'percregtmp parametri)))
  (start)
  (setq nome nil)
  (while (null nome)
    (setq ent (car (entsel)))
    (if (= "codpas" (cdr (assoc '2 (entget ent))))
      (setq nome (cdr (assoc '1 (entget (entnext ent)))))
      (alert "Selezione non valida")
    )
  )
  (SETQ NEWP NIL)
  (IF (FINDFILE (STRCAT (cadr (assoc 'perc_assiemi parametri)) NOME ".DWG"))
    (PROGN
      (INITGET "Si No")
      (setq sn (getkword "\nPannello già disegnato lo ridisegno [No/Si]:"))
      (if (= sn "Si")
	(progn
	  (vl-file-delete (STRCAT (cadr (assoc 'perc_assiemi parametri)) NOME ".dwg"))
          (SETQ NEWP "T")
	)
	(progn
          (SETQ FILE (OPEN (strcat "c:\\acad_tmp\\OPENPAN.SCR") "W"))
	  (WRITE-LINE (STRCAT "_OPEN "(cadr (assoc 'perc_assiemi parametri)) NOME) FILE)
	  (WRITE-LINE "_LAYOUT _SET A4" FILE)
	  (CLOSE FILE)
	)
      )
    )
    (PROGN
      (SETQ NEWP "T")
    )
  )
(IF NEWP
  (PROGN
    (SETQ FILE (OPEN (strcat "c:\\acad_tmp\\NEWPAN.SCR") "W"))
    (WRITE-LINE (strcat "_NEW " "PANNELLO") FILE)
    (if siglarif (write-line (strcat "(setq siglarif \"" siglarif "\")")file))
    (WRITE-LINE "(LOAD\"ACAD\")" FILE)
    (WRITE-LINE (STRCAT "DISPAs " NOME) FILE)
    (WRITE-LINE (STRCAT "_LAYOUT _SET A4 _SAVEAS 2000 "(cadr (assoc 'perc_assiemi parametri)) NOME " _close") FILE)
    (CLOSE FILE)
    (COMMAND "SCRIPT" "c:\\acad_tmp\\NEWPAN")
  )
  (COMMAND "SCRIPT" "c:\\acad_tmp\\OPENPAN")
)
  (stop)
)
(DEFUN c:NEWPAS ()
  (IF (/= MODALITA (cadr (assoc 'percregtmp parametri))) (C:ANNTAB))
  (setq modalita (cadr (assoc 'percregtmp parametri)))
  (start)
  (prompt "\nSelezionare o Invio per disegnare solo i nuovi")
  (setq gr (ssget (list '(0 . "INSERT") '(2 . "codpas") '(8 . "siglepan"))))
  (if gr
    (progn
	  (setq nr 0)
	  (setq lisnom nil)
	  (setq 1gia nil)
	  (while (setq ent (ssname gr nr))
	    (setq nome (cdr (assoc '1 (entget (entnext ent)))))
	    (if (null (member nome lisnom)) (setq lisnom (cons nome lisnom)))
	    (IF (FINDFILE (STRCAT (cadr (assoc 'perc_assiemi parametri)) NOME ".DWG")) (setq 1gia "t"))
	    (setq nr (+ 1 nr))
	  )
	  (if 1gia
	    (progn
	      (INITGET "Si No")
	      (setq sn (getkword "\nPannello già disegnato lo ridisegno [No/Si]:"))
	    )
	    (setq sn "Si")
	  )
    )
    (progn
      (setq lisnom_ $pannelli)
      (SETQ lisnom NIL)
      (FOREACH NM lisnom_
	(if (null (member nm lisnom)) (Setq lisnom (cons nm lisnom)))
	)
      (setq $pannelli nil)
      (if (null lisnom) (progn (alert "Niente di nuovo") (exit)))
      (setq sn "Si")
    )
  )
  (if (= sn "Si")
    (progn
        (SETQ FILE (OPEN (strcat "c:\\acad_tmp\\newpan.SCR") "W"))
;;;          (FINDFILE (STRCAT (cadr (assoc 'perc_assiemi parametri)) NOME ".DWG"))
          (WRITE-LINE (strcat "_NEW " "PANNELLO") FILE)
     (if siglarif (write-line (strcat "(setq siglarif \"" siglarif "\")")file))
          (WRITE-LINE "(LOAD\"ACAD\")" FILE)
        (foreach nome lisnom
	  (write-line "_setvar tilemode 1" file)
          (vl-file-delete (STRCAT (cadr (assoc 'perc_assiemi parametri)) NOME ".dwg"))
          (WRITE-LINE (STRCAT "DISPAs " NOME) FILE)
          (WRITE-LINE (STRCAT "_LAYOUT _SET A4 _SAVEAS 2000 "(cadr (assoc 'perc_assiemi parametri)) NOME) FILE)
        )
        (write-line "_close" file)
        (CLOSE FILE)
        (COMMAND "SCRIPT" "c:\\acad_tmp\\newPAN")
    )
  )
  (stop)
)
