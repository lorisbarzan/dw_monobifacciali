(defun c:specchiacab ()
  (setq modop_d nil)
  (command "_layer" "_ON" "traccia" "")
  (setq punto1 (getpoint "\nPunto Uno"))
  (setq punto2 (getpoint punto1 "\nPunto Due"))
  (setq oggetti (ssget "x" (list '(0 . "LWPOLYLINE") '(8 . "traccia"))))
  (setq nr -1)
  (setq og_ nil)
  (while (and oggetti (setq og_ (ssname oggetti (setq nr (+ 1 nr)))))
    (command "_mirror" og_ "" "_non" punto1 "_non" punto2 "_n")
    (setq og (entlast))
    (setq lispt nil) (FOREACH N (ENTGET og) (IF (= '10 (CAR N)) (SETQ LISPT (CONS (CDR N) LISPT))))
    (if (or (= 128 (cdr (assoc '70 (entget og)))) (= 0 (cdr (assoc '70 (entget og))))) (setq ch nil) (setq ch t))
    (command "_layer" "_m" "traccia" "")
    (command "_pline")
    (foreach pt lispt
      (command "_non" pt)
    )
    (if ch (command "_close"))
    (entdel og)
  )
  (if oggetti (command "_erase" oggetti ""))
  (setq oggetti (ssget "x" (list '(0 . "INSERT") '(2 . "Porta*"))))
  (setq nr -1)
  (while (and oggetti (setq og_ (ssname oggetti (setq nr (+ 1 nr)))))
    (command "_mirror" og_ "" "_non" punto1 "_non" punto2 "_n")
    (setq og (entlast))
    (setq pt (cdr (assoc '10 (entget og))))
    (setq ang (cdr (assoc '50 (entget og))))
    (command "_mirror" og "" "_non" pt  "_non" (polar pt (+ (/ pi 2) ang) 300) "_y")
  )
  (if oggetti (command "_erase" oggetti ""))
  (setq oggetti (ssget "x" (list '(0 . "INSERT") '(2 . "Profilo*"))))
  (setq nr -1)
  (while (and oggetti (setq og_ (ssname oggetti (setq nr (+ 1 nr)))))
    (command "_mirror" og_ "" "_non" punto1 "_non" punto2 "_n")
    (setq og (entlast))
    (setq pt (cdr (assoc '10 (entget og))))
    (setq ang (cdr (assoc '50 (entget og))))
    (command "_mirror" og "" "_non" pt  "_non" (polar pt (+ (/ pi 2) ang) 300) "_y")
  )
  (if oggetti (command "_erase" oggetti ""))
  (setq oggetti (ssget "x" (list '(0 . "INSERT") '(2 . "DIVIDI*"))))
  (setq nr -1)
  (while (and oggetti (setq og_ (ssname oggetti (setq nr (+ 1 nr)))))
    (command "_mirror" og_ "" "_non" punto1 "_non" punto2 "_n")
    (setq og (entlast))
    (setq pt (cdr (assoc '10 (entget og))))
    (setq ang (cdr (assoc '50 (entget og))))
    (command "_mirror" og "" "_non" pt  "_non" (polar pt (+ (/ pi 2) ang) 300) "_y")
    (setq ent1 (entlast))
    (command "_ROTATE" ENT1 "" "_non" pt "180")
    (cond 
      ((= "DIVIDISX" (cdr (assoc '2 (entget og))))
       (progn
         (setq ed (entget ent1))
         (setq ed (subst (cons 2 "DIVIDIDX") (assoc 2 ed) ed ))
         (entmod ed)
       )
      )
      ((= "DIVIDIDX" (cdr (assoc '2 (entget og))))
       (progn
         (setq ed (entget ent1))
         (setq ed (subst (cons 2 "DIVIDISX") (assoc 2 ed) ed ))
         (entmod ed)
       )
      )
	  )
  )

  (if oggetti (command "_erase" oggetti ""))
  (setq oggetti (ssget "x" (list '(0 . "INSERT") '(2 . "FORO*"))))
  (setq nr -1)
  (while (and oggetti (setq og_ (ssname oggetti (setq nr (+ 1 nr)))))
    (command"_mirror" og_ "" "_non" punto1 "_non" punto2 "_n")
    (setq og (entlast))
    (setq pt (cdr (assoc '10 (entget og))))
    (setq ang (cdr (assoc '50 (entget og))))
    (command"_mirror" og "" "_non" pt  "_non" (polar pt (+ (/ pi 2) ang) 300) "_y")
    (setq ent1 (entlast))

    
  )
  (if oggetti (command "_erase" oggetti ""))
  (setq oggetti (ssget "x" (list '(0 . "MLINE") '(8 . "rinforzi") '(2 . "RINFORZO-*"))))
  (setq nr -1)
  (while (and oggetti (setq og_ (ssname oggetti (setq nr (+ 1 nr)))))
    (setq lispt nil) (FOREACH N (ENTGET og_) (IF (= '11 (CAR N)) (SETQ LISPT (CONS (CDR N) LISPT))))
    (command "_mirror" og_ "" "_non" punto1 "_non" punto2 "_n")
    (setq ogX (entlast))
    (setq lispt nil) (FOREACH N (ENTGET ogX) (IF (= '11 (CAR N)) (SETQ LISPT (CONS (CDR N) LISPT))))
    (setq pm (polar (nth 1 lispt) (angle (nth 1 lispt) (nth 0 lispt))(/ (distance (nth 0 lispt) (nth 1 lispt)) 2) ))
    (command "_mirror" ogx "" "_non" pm "_non" (polar pm  (- (angle (nth 1 lispt) (nth 0 lispt)) (/ pi 2)) 100) "_y")
  )
  (if oggetti (command "_erase" oggetti ""))

  (setq oggetti (ssget "x" (list '(0 . "INSERT") '(2 . "Rinforzo-*"))))
  (setq nr -1)
  (while (and oggetti (setq og_ (ssname oggetti (setq nr (+ 1 nr)))))
    (command "_mirror" og_ "" "_non" punto1 "_non" punto2 "_n")
    (setq og (entlast))
    (setq pt (cdr (assoc '10 (entget og))))
    (setq ang (cdr (assoc '50 (entget og))))
    (command "_mirror" og "" "_non" pt  "_non" (polar pt (+ (/ pi 2) ang) 300) "_y")
    (setq ent1 (entlast))
  )
  (if oggetti (command "_erase" oggetti ""))

  (setq oggetti (ssget "x" (list '(0 . "LWPOLYLINE") '(8 . "pannelli-*"))))
  (setq nr -1)
  (command "_ZOOM" "_e")
  (setvar "pickstyle" 0)
  (while (and oggetti (setq og_ (ssname oggetti (setq nr (+ 1 nr)))))
    (command "_mirror" og_ "" "_non" punto1 "_non" punto2 "_n")
    (setq og (entlast))
    (setq lispt nil) (FOREACH N (ENTGET og) (IF (= '10 (CAR N)) (SETQ LISPT (CONS (CDR N) LISPT))))
    (setq lispt (reverse lispt))
    (setq pm1 (nth 0 lispt))
    (setq pm2 (nth 1 lispt))
    (setq pm3 (nth 2 lispt))
    (setq modo (leggi og "PANTIP"))
    (setq fpan (leggi og "PANFIN"))
    (setq hpan (cdr (assoc '39 (entget og))))
    (setq zpan (cdr (assoc '38 (entget og))))
    (setq tipomb (leggi og "TIPOMB"))
          
    (if (= "pannelli-dritti" (cdr (assoc '8 (entget og))))
      (cond 
        ((and (= modo "STD") (= nil (cercaSPC pm2 PM1)) (= nil (cercaSPC pm1 PM2))) (SPPAN PM2 PM1 "STD" hpan fpan zpan) (allega entlastpan "PANTIP" "STD"))
        ((and (= modo "STD") (= "T" (cercaSPC pm2 PM1)) (= nil (cercaSPC pm1 PM2))) (SPPAN PM2 PM1 "STD" hpan fpan zpan) (allega entlastpan "PANTIP" "STD"))
        ((and (= modo "STD") (= "T" (cercaSPC pm2 PM1)) (= "T" (cercaSPC pm1 PM2))) (SPPAN PM2 PM1 "SPC" hpan fpan zpan) (allega entlastpan "PANTIP" "SPC"))
        ((and (= modo "STD") (= nil (cercaSPC pm2 PM1)) (= "T" (cercaSPC pm1 PM2))) (SPPAN PM2 PM1 "SPC" hpan fpan zpan) (allega entlastpan "PANTIP" "SPC"))
        ((and (= modo "SPC") (= nil (cercaSPC pm2 PM1)) (= nil (cercaSPC pm1 PM2))) (SPPAN PM2 PM1 "SPC" hpan fpan zpan) (allega entlastpan "PANTIP" "SPC"))
        ((and (= modo "SPC") (= "T" (cercaSPC pm2 PM1)) (= nil (cercaSPC pm1 PM2))) (SPPAN PM2 PM1 "STD" hpan fpan zpan) (allega entlastpan "PANTIP" "STD"))
        ((and (= modo "SPC") (= "T" (cercaSPC pm2 PM1)) (= "T" (cercaSPC pm1 PM2))) (SPPAN PM2 PM1 "SPC" hpan fpan zpan) (allega entlastpan "PANTIP" "SPC"))
        ((and (= modo "SPC") (= nil (cercaSPC pm2 PM1)) (= "T" (cercaSPC pm1 PM2))) (SPPAN PM2 PM1 "SPC" hpan fpan zpan) (allega entlastpan "PANTIP" "SPC"))
        ((and (= modo "SPM") (= nil (cercaSPC pm2 PM1)) (= nil (cercaSPC pm1 PM2))) (SPPAN PM2 PM1 "SPM" hpan fpan zpan) (allega entlastpan "PANTIP" "SPM"))
        ((and (= modo "SPM") (= "T" (cercaSPC pm2 PM1)) (= nil (cercaSPC pm1 PM2))) (SPPAN PM2 PM1 "STD" hpan fpan zpan) (allega entlastpan "PANTIP" "STD"))
        ((and (= modo "SPM") (= "T" (cercaSPC pm2 PM1)) (= "T" (cercaSPC pm1 PM2))) (SPPAN PM2 PM1 "SPC" hpan fpan zpan) (allega entlastpan "PANTIP" "SPC"))
        ((and (= modo "SPM") (= nil (cercaSPC pm2 PM1)) (= "T" (cercaSPC pm1 PM2))) (SPPAN PM2 PM1 "SPC" hpan fpan zpan) (allega entlastpan "PANTIP" "SPC"))
        ((= modo "MAN") 
         (SETQ VAL (LEGGI OG "SVILMAN")) 
         (SPPAN PM2 PM1 "MAN" hpan fpan zpan) 
         (allega entlastpan "PANTIP" "MAN") 
         (SETQ LVAL (READ VAL))
         (SETQ VAL (STRCAT "(" (RTOS (NTH 1 LVAL) 2 1) " " (RTOS (NTH 0 LVAL) 2 1) " " (RTOS (NTH 2 LVAL) 2 1) " " (RTOS (NTH 3 LVAL) 2 1) ")"))
         (ALLEGA ENTLASTPAN "SVILMAN" VAL)
         )
        ((and (= modo "MTD") (= nil (cercaSPC pm2 PM1)) (= nil (cercaSPC pm1 PM2))) (SPPAN PM2 PM1 "MTD" hpan fpan zpan) (allega entlastpan "PANTIP" "MTD"))
        ((and (= modo "MTD") (= "T" (cercaSPC pm2 PM1)) (= nil (cercaSPC pm1 PM2))) (SPPAN PM2 PM1 "MTD" hpan fpan zpan) (allega entlastpan "PANTIP" "MTD"))
        ((and (= modo "MTD") (= "T" (cercaSPC pm2 PM1)) (= "T" (cercaSPC pm1 PM2))) (SPPAN PM2 PM1 "MPC" hpan fpan zpan) (allega entlastpan "PANTIP" "MPC"))
        ((and (= modo "MTD") (= nil (cercaSPC pm2 PM1)) (= "T" (cercaSPC pm1 PM2))) (SPPAN PM2 PM1 "MPC" hpan fpan zpan) (allega entlastpan "PANTIP" "MPC"))
        ((and (= modo "MPC") (= nil (cercaSPC pm2 PM1)) (= nil (cercaSPC pm1 PM2))) (SPPAN PM2 PM1 "MPC" hpan fpan zpan) (allega entlastpan "PANTIP" "MPC"))
        ((and (= modo "MPC") (= "T" (cercaSPC pm2 PM1)) (= nil (cercaSPC pm1 PM2))) (SPPAN PM2 PM1 "MTD" hpan fpan zpan) (allega entlastpan "PANTIP" "MTD"))
        ((and (= modo "MPC") (= "T" (cercaSPC pm2 PM1)) (= "T" (cercaSPC pm1 PM2))) (SPPAN PM2 PM1 "MPC" hpan fpan zpan) (allega entlastpan "PANTIP" "MPC"))
        ((and (= modo "MPC") (= nil (cercaSPC pm2 PM1)) (= "T" (cercaSPC pm1 PM2))) (SPPAN PM2 PM1 "MPC" hpan fpan zpan) (allega entlastpan "PANTIP" "MPC"))
        ((and (= modo "MPM") (= nil (cercaSPC pm2 PM1)) (= nil (cercaSPC pm1 PM2))) (SPPAN PM2 PM1 "MPM" hpan fpan zpan) (allega entlastpan "PANTIP" "MPM"))
        ((and (= modo "MPM") (= "T" (cercaSPC pm2 PM1)) (= nil (cercaSPC pm1 PM2))) (SPPAN PM2 PM1 "MTD" hpan fpan zpan) (allega entlastpan "PANTIP" "MTD"))
        ((and (= modo "MPM") (= "T" (cercaSPC pm2 PM1)) (= "T" (cercaSPC pm1 PM2))) (SPPAN PM2 PM1 "MPC" hpan fpan zpan) (allega entlastpan "PANTIP" "MPC"))
        ((and (= modo "MPM") (= nil (cercaSPC pm2 PM1)) (= "T" (cercaSPC pm1 PM2))) (SPPAN PM2 PM1 "MPC" hpan fpan zpan) (allega entlastpan "PANTIP" "MPC"))
      )
      (cond
        ((and (= modo "STD") (= nil (cercaSPC pm3 PM2)) (= nil (cercaSPC pm1 pM2))) (SPANG PM3 PM2 PM1 "STD" hpan fpan zpan) (allega entlastpan "PANTIP" "STD"))
        ((and (= modo "STD") (= "T" (cercaSPC pm3 PM2)) (= nil (cercaSPC pm1 pM2))) (SPANG PM3 PM2 PM1 "STD" hpan fpan zpan) (allega entlastpan "PANTIP" "STD"))
        ((and (= modo "STD") (= "T" (cercaSPC pm3 PM2)) (= "T" (cercaSPC pm1 pM2))) (SPANG PM3 PM2 PM1 "SPC" hpan fpan zpan) (allega entlastpan "PANTIP" "SPC"))
        ((and (= modo "STD") (= nil (cercaSPC pm3 PM2)) (= "T" (cercaSPC pm1 pM2))) (SPANG PM3 PM2 PM1 "SPC" hpan fpan zpan) (allega entlastpan "PANTIP" "SPC"))
        ((and (= modo "SPC") (= nil (cercaSPC pm3 PM2)) (= nil (cercaSPC pm1 pM2))) (SPANG PM3 PM2 PM1 "SPC" hpan fpan zpan) (allega entlastpan "PANTIP" "SPC"))
        ((and (= modo "SPC") (= "T" (cercaSPC pm3 PM2)) (= nil (cercaSPC pm1 pM2))) (SPANG PM3 PM2 PM1 "STD" hpan fpan zpan) (allega entlastpan "PANTIP" "STD"))
        ((and (= modo "SPC") (= "T" (cercaSPC pm3 PM2)) (= "T" (cercaSPC pm1 pM2))) (SPANG PM3 PM2 PM1 "SPC" hpan fpan zpan) (allega entlastpan "PANTIP" "SPC"))
        ((and (= modo "SPC") (= nil (cercaSPC pm3 PM2)) (= "T" (cercaSPC pm1 pM2))) (SPANG PM3 PM2 PM1 "SPC" hpan fpan zpan) (allega entlastpan "PANTIP" "SPC"))
        ((and (= modo "SPM") (= nil (cercaSPC pm3 PM2)) (= nil (cercaSPC pm1 pM2))) (SPANG PM3 PM2 PM1 "SPM" hpan fpan zpan) (allega entlastpan "PANTIP" "SPM"))
        ((and (= modo "SPM") (= "T" (cercaSPC pm3 PM2)) (= nil (cercaSPC pm1 pM2))) (SPANG PM3 PM2 PM1 "STD" hpan fpan zpan) (allega entlastpan "PANTIP" "STD"))
        ((and (= modo "SPM") (= "T" (cercaSPC pm3 PM2)) (= "T" (cercaSPC pm1 pM2))) (SPANG PM3 PM2 PM1 "SPC" hpan fpan zpan) (allega entlastpan "PANTIP" "SPC"))
        ((and (= modo "SPM") (= nil (cercaSPC pm3 PM2)) (= "T" (cercaSPC pm1 pM2))) (SPANG PM3 PM2 PM1 "SPC" hpan fpan zpan) (allega entlastpan "PANTIP" "SPC"))
        ((= modo "MAN") 
         (SPANG PM3 PM2 PM1 "MAN" hpan fpan zpan)
         (allega entlastpan "PANTIP" "MAN")
         (SETQ VAL (LEGGI OG "SVILMAN"))
         (SETQ LVAL (READ VAL))
         (SETQ VAL (STRCAT "(" (RTOS (NTH 1 LVAL) 2 1) " " (RTOS (NTH 0 LVAL) 2 1) " " (RTOS (NTH 2 LVAL) 2 1) " " (RTOS (NTH 3 LVAL) 2 1) ")"))
         (ALLEGA ENTLASTPAN "SVILMAN" VAL)
         )
        ((and (= modo "MTD") (= nil (cercaSPC pm3 PM2)) (= nil (cercaSPC pm1 pM2)))	(SPANG PM3 PM2 PM1 "MTD" hpan fpan zpan) (allega entlastpan "PANTIP" "MTD"))
        ((and (= modo "MTD") (= "T" (cercaSPC pm3 PM2)) (= nil (cercaSPC pm1 pM2))) (SPANG PM3 PM2 PM1 "MTD" hpan fpan zpan) (allega entlastpan "PANTIP" "MTD"))
        ((and (= modo "MTD") (= "T" (cercaSPC pm3 PM2)) (= "T" (cercaSPC pm1 pM2))) (SPANG PM3 PM2 PM1 "MPC" hpan fpan zpan) (allega entlastpan "PANTIP" "MPC"))
        ((and (= modo "MTD") (= nil (cercaSPC pm3 PM2)) (= "T" (cercaSPC pm1 pM2))) (SPANG PM3 PM2 PM1 "MPC" hpan fpan zpan) (allega entlastpan "PANTIP" "MPC"))
        ((and (= modo "MPC") (= nil (cercaSPC pm3 PM2)) (= nil (cercaSPC pm1 pM2))) (SPANG PM3 PM2 PM1 "MPC" hpan fpan zpan) (allega entlastpan "PANTIP" "MPC"))
        ((and (= modo "MPC") (= "T" (cercaSPC pm3 PM2)) (= nil (cercaSPC pm1 pM2))) (SPANG PM3 PM2 PM1 "MTD" hpan fpan zpan) (allega entlastpan "PANTIP" "MTD"))
        ((and (= modo "MPC") (= "T" (cercaSPC pm3 PM2)) (= "T" (cercaSPC pm1 pM2))) (SPANG PM3 PM2 PM1 "MPC" hpan fpan zpan) (allega entlastpan "PANTIP" "MPC"))
        ((and (= modo "MPC") (= nil (cercaSPC pm3 PM2)) (= "T" (cercaSPC pm1 pM2))) (SPANG PM3 PM2 PM1 "MPC" hpan fpan zpan) (allega entlastpan "PANTIP" "MPC"))
        ((and (= modo "MPM") (= nil (cercaSPC pm3 PM2)) (= nil (cercaSPC pm1 pM2))) (SPANG PM3 PM2 PM1 "MPM" hpan fpan zpan) (allega entlastpan "PANTIP" "MPM"))
        ((and (= modo "MPM") (= "T" (cercaSPC pm3 PM2)) (= nil (cercaSPC pm1 pM2))) (SPANG PM3 PM2 PM1 "MTD" hpan fpan zpan) (allega entlastpan "PANTIP" "MTD"))
        ((and (= modo "MPM") (= "T" (cercaSPC pm3 PM2)) (= "T" (cercaSPC pm1 pM2))) (SPANG PM3 PM2 PM1 "MPC" hpan fpan zpan) (allega entlastpan "PANTIP" "MPC"))
        ((and (= modo "MPM") (= nil (cercaSPC pm3 PM2)) (= "T" (cercaSPC pm1 pM2))) (SPANG PM3 PM2 PM1 "MPC" hpan fpan zpan) (allega entlastpan "PANTIP" "MPC"))
      )
    )
    (allega entlastpan "TIPOMB" tipomb)
    (if (= tipomb "Monofacciale") (command "_chprop" entlastpan "" "_p" "_co" 6 "" ) (command "_chprop" (entlast) "" "_p" "_co" 7 ""))
    ; (if (= tipomb "Bifacciale") (command "_chprop" entlastpan "" "_p" "_co" 6 "" ) (command "_chprop" (entlast) "" "_p" "_co" 7 ""))
    (entdel og)
  )
  (setvar "pickstyle" 1)
  (if oggetti (command "_erase" oggetti ""))
  (vai_l "siglepan")
  (setq oggetti (ssget "x" (list '(0 . "insert") '(8 . "siglepan"))))
  (if oggetti (command "_erase" oggetti ""))
  (torna_l)
  (vai_l "0")
  (setq oggetti (ssget "x" (list '(0 . "circle") '(8 . "0"))))
  (if oggetti (command "_erase" oggetti ""))
  (setq oggetti nil)
  (torna_l)
  (c:retro)
  (stop)
)
