(defun c:CorreggiCabPan ()
  (vl-file-delete (strcat modalita "cabpan_.bak"))
  (vl-file-copy  (strcat modalita "cabpan.txt")  (strcat modalita "cabpan_.bak"))
  (setq filer (S_OPEN (strcat modalita "cabpan_.bak") "r"))
  (setq filew (S_OPEN (strcat modalita "cabpan.txt") "w"))
  (while (setq rig (read-line filer))
   (setq lun (length (read (strcat "(" rig ")"))))
   (repeat (- 12 lun) (setq rig (strcat rig "\t\"NULL\"" )))
         (write-line rig filew)
	)
  (s_close filer (strcat modalita "cabpan_.bak"))
  (s_close filew (strcat modalita "cabpan.txt"))
)
